(defun c:bup(/ tm no o_get o_number os i ed basepoint xscale)
  (if (= ly_scale nil) (c:tl))
  (setq tm (getvar "TILEMODE"))
  (if (= tm 0) (setvar "TILEMODE" 1))
  (setq o_get (ssget '((0 . "INSERT"))))
  (setq o_number (sslength o_get))
  (setq no 0)
  (setq os (getvar "OSMODE"))
  (setvar "OSMODE" 0)
  (while (< no o_number)
     (progn
       (setq i (ssname o_get no))
       (setq ed (entget i))
       (if (= (cdr (assoc 0 ed)) "INSERT")
	 (progn
	   (setq basepoint (cdr (assoc 10 (entget i))))
	   (setq xscale (abs (cdr (assoc 41 (entget i)))))
	   (command ".scale" i "" basepoint (/ 1 xscale))
	   (command ".scale" i "" basepoint ly_scale)
	   )
	 )
       (setq no (+ no 1))
       )
    )
  (setvar "OSMODE" os)
  )
;;;;;;;;;;;;;;;;;;;;;;;;;;;;;;;;;;;;;;;;;;;
(defun bup(o_get / tm no o_number os i ed basepoint xscale)
  (if (= ly_scale nil) (c:tl))
  (setq tm (getvar "TILEMODE"))
  (if (= tm 0) (setvar "TILEMODE" 1))
  (setq o_number (sslength o_get))
  (setq no 0)
  (setq os (getvar "OSMODE"))
  (setvar "OSMODE" 0)
  (while (< no o_number)
    (progn
      (setq i (ssname o_get no))
      (setq ed (entget i))
      (if (= (cdr (assoc 0 ed)) "INSERT")
	(progn
	  (setq basepoint (cdr (assoc 10 (entget i))))
	  (setq xscale (abs (cdr (assoc 41 (entget i)))))
	  (command ".scale" i "" basepoint (/ 1 xscale))
	  (command ".scale" i "" basepoint ly_scale)
	)
      )
      (setq no (+ no 1))
    )
  )
  (setvar "OSMODE" os)
)
;;;;;;;;;;;;;;;;;;;;;;;;;;;;;;;;;;;;;;;;;;;
(defun c:sect(/ ss os p1 p2 str1 str2)
  (setq ss (ssadd))
  (setq unit (getvar "INSUNITS"))
  (setvar "INSUNITS" 4)
  (if (= ly_scale nil) (c:tl))
  (setq p1 (getpoint "\nStart:  "))
  (setq p2 (getpoint "\nEnd:  " p1))
  (setq os (getvar "OSMODE"))
  (setvar "OSMODE" 0)
  (setq str1 "-")
  (setq str1 (getstring "\nDrawing Number<->:  "))
  (setq str2 "A")
  (setq str2 (getstring "\nSection Letter<A>:  "))
  (command ".insert" "Section_start.dwg" p1 ly_scale ly_scale "" str1 str2)
  (setq ss (ssadd (entlast) ss))
  (command ".insert" "Section_direction.dwg" p1 ly_scale ly_scale (* (/ (angle p1 p2) pi) 180))
  (setq ss (ssadd (entlast) ss))
  (command ".insert" "Section_end.dwg" p2 ly_scale ly_scale (* (/ (angle p1 p2) pi) 180))
  (setq ss (ssadd (entlast) ss))
  (setvar "OSMODE" os)
  (setvar "INSUNITS" unit)
  (bup ss)
)
;;;;;;;;;;;;;;;;;;;;;;;;;;;;;;;;;;;;;;;;;;
(defun c:secs(/ ss p1 str1 str2 str3)
  (setq ss (ssadd))
  (setq unit (getvar "INSUNITS"))
  (setvar "INSUNITS" 4)
  (if (= ly_scale nil) (c:tl))
  (setq p1 (getpoint "\nStart:  "))
  (setq os (getvar "OSMODE"))
  (setvar "OSMODE" 0)
  (setq str1 "?")
  (setq str1 (getstring "\nEnter Section Letter<?>:  "))
  (setq str2 "1:50")
  (setq str2 (getstring "\nEnter Scale<1:50>:  "))
  (setq str3 "-")
  (setq str3 (getstring "\nEnter Drawing No.<->:  "))
  (command ".insert" "Section_show.dwg" p1 ly_scale ly_scale "" str1 str2 str3)
  (setq ss (ssadd (entlast) ss))
  (bup ss)
  (setvar "OSMODE" os)
  (setvar "INSUNITS" unit)

)
;;;;;;;;;;;;;;;;;;;;;;;;;;;;;;;;;;;;;;;;;;;;;
(defun c:dets(/ ss os unit p1 str1 str2 str3)
  (setq unit (getvar "INSUNITS"))
  (setq ss (ssadd))
  (setvar "INSUNITS" 4)
  (if (= ly_scale nil) (c:tl))
  (setq p1 (getpoint "\nStart:  "))
  (setq os (getvar "OSMODE"))
  (setvar "OSMODE" 0)
  (setq str1 "?")
  (setq str1 (getstring "\nEnter Detail Letter<A>:  "))
  (setq str2 "1:50")
  (setq str2 (getstring "\nEnter Scale<1:50>:  "))
  (setq str3 "-")
  (setq str3 (getstring "\nEnter Drawing No.<->:  "))
  (command ".insert" "Detail_show.dwg" p1 ly_scale ly_scale "" str1 str2 str3)
  (setq ss (ssadd (entlast) ss))
  (bup ss)
  (setvar "OSMODE" os)
  (setvar "INSUNITS" unit)

)
;;;;;;;;;;;;;;;;;;;;;;;;;;;;;;;;;;;;;;;;;;
(defun c:det(/ p1 p2 p3 p4 P5 str1 str2)
  (setq unit (getvar "INSUNITS"))
  (setvar "INSUNITS" 4)
  (if (= ly_scale nil) (c:tl))
  (setq p1 (getpoint "\nStart:  "))
  (setq p2 (getpoint "\nStart:  " p1))
  (setq os (getvar "OSMODE"))
  (setvar "OSMODE" 0)
  (setq ss (ssadd))
  (setq str1 "?")
  (setq str1 (getstring "\nEnter Detail Letter<A>:  "))
  (setq str2 "-")
  (setq str2 (getstring "\nEnter Drawing No.<->:  "))
  (if (<= 0 (- (car p2) (car p1)))
    (progn
      (command ".Pline" p1 p2 "")
      (command ".insert" "Detail_l.dwg" p2 ly_scale ly_scale "" str2 str1)
      (setq ss (ssadd (entlast) ss))
      (bup ss)
    )
  )
  (if (> 0 (- (car p2) (car p1)))
    (progn
      (command ".Pline" p1 p2 "")
      (command ".insert" "Detail_r.dwg" p2 ly_scale ly_scale "" str2 str1)
      (setq ss (ssadd (entlast) ss))
      (bup ss)
    )
  )
  (mt p1 p2)
  (setvar "OSMODE" os)
  (setvar "INSUNITS" unit)
)
;;;;;;;;;;;;;;;;;;;;;;;;;;;;;;;;;;;;;;;;;;;;;;;
(defun c:mt(/ ss p1 p2)
  (setq ss (ssadd))
  (setq unit (getvar "INSUNITS"))
  (setvar "INSUNITS" 4)
  (if (= ly_scale nil) (c:tl))
  (setq p1 (getpoint "\nInsert Point:  "))
  (setq p2 (getpoint "\nDirection:  " p1))
  (command ".insert" "arrow1.5.dwg" p1 ly_scale ly_scale p2)
  (setq ss (ssadd (entlast) ss))
  (bup ss)
  (setvar "INSUNITS" unit)
)
;;;;;;;;;;;;;;;;;;;;;;;;;;;;;;;;;;;;;;;;;;;;;;;
(defun mt(p1 p2)
  (setq ss (ssadd))
  (if (= ly_scale nil) (c:tl))
  (setq unit (getvar "INSUNITS"))
  (setvar "INSUNITS" 4)
  (command ".insert" "arrow1.5.dwg" p1 ly_scale ly_scale p2)
  (setq ss (ssadd (entlast) ss))
  (bup ss)
  (setvar "INSUNITS" unit)
)
;;;;;;;;;;;;;;;;;;;;;;;;;;;;;;;;;;;;;;;;;;;;;;;
(defun USTR (bit msg def spflag / inp nval)
     (if (and def (/= def ""))
          (setq msg (strcat "\n" msg "<" def ">: ")
               inp (getstring spflag msg)
               inp (if (= inp "") def inp)
          )
          (progn
               (if (= " " (substr msg (strlen msg) 1))
                    (setq msg (strcat "\n" (substr msg 1 (1- (strlen msg))) ": "))
                    (setq msg (strcat "\n" msg ": "))
               )
               (if (= bit 1)
                    (while (= "" (setq inp (getstring spflag msg)))
                         (prompt "\nInvalid String.")
                    )
                    (setq inp (getstring spflag msg))
               )
          )
     )
     inp
)
;;;;;;;;;;;;;;;;;;;;;;;;;;;;;;;;;;;;;;;;;;;;;;;;;;;;;;;;;;;;;;;;;;;;;;;;;;;;;;;;;;;;;;;;;
(Defun matsosanh(/ pt cao)
  (prompt "\nKhai báo M\U+1EB7t So Sánh")
  (setq pt (getpoint "\nXác \U+0111\U+1ECBnh \U+0110i\U+1EC3m: "))
  (setq cao (getreal "\nCao \U+0111\U+1ED9 c\U+1EE7a \U+0110i\U+1EC3m: "))
  (setq #mss (- (cadr pt) cao))
)
(defun c:#mss() (matsosanh))
;;;;;;;;;;;;;;;;;;;;;;;;;;;;;;;;;;;;;;;;;;;;;;;;;;;;;;;
(defun c:elevation(/ ss unit cl dz ot pt ptside ang y)
  (if ( = #mss nil) (matsosanh))
  (setq ss (ssadd))
  (setq unit (getvar "INSUNITS"))
  (setvar "INSUNITS" 4)
  (if (= #Bacc nil) (setq #Bacc (getint "\nPh\U+1EA7n th\U+1EADp phân: ")))
  (setq CL (getvar "clayer"))
  (setvar "CLAYER" "0") 	
  (setq DZ (getvar "DIMZIN"))
  (setvar "DIMZIN" 0)
  (setq OT (getvar "ORTHOMODE"))
  (setvar "ORTHOMODE" 0)
  (setq pt (getpoint "\n\U+0110i\U+1EC3m l\U+1EA5y Cao \U+0111\U+1ED9: ")
	ptside (getpoint "\nH\U+01B0\U+1EDBng: " pt)
	ang (angle pt ptside)
  )
  (setq y (- (cadr pt) #mss))
  (cond
    ((> y 0) (setq y (strcat "+" (rtos y 2 #Bacc))))
    ((< y 0) (setq y (rtos y 2 #Bacc)))
    ((= y 0) (setq y "%%p0.00"))
    )
  (setq y (ustr 0 "\nCao \U+0111\U+1ED9 \U+0110i\U+1EC3m là: " y T))
  (if (AND (>= ang 0) (< ang 1.5708)) (command ".INSERT" "Elevation" pt ly_scale ly_scale "0" y))
     ( if	 (AND (>= ang 1.5708) (< ang 3.1416)) (command ".INSERT" "Elevation3" pt ly_scale ly_scale "0" y))
     ( if	 (AND (>= ang 3.1416) (< ang 4.7124)) (command ".INSERT" "Elevation2" pt ly_scale ly_scale "0" y))
     ( if	 (AND (>= ang 4.7124) (< ang 6.2832)) (command ".INSERT" "Elevation1" pt ly_scale ly_scale "0" y))
  (setq ss (ssadd (entlast) ss))
  (bup ss)
  (setvar "DIMZIN" DZ)
  (setvar "ORTHOMODE" OT)
  (setvar "CLAYER" CL)
  (setvar "INSUNITS" unit)
)
(defun c:ev() (c:elevation))

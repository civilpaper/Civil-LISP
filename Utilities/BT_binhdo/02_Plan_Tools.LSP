(defun c:quay(/ goc gocrad sst ti en)
  (setq goc (getreal "\nXac dinh goc quay: "))
  (setq gocrad (/ (* goc pi) 180))
  (setq sst (ssget '((0 . "TEXT"))))
  (setq ti 0)
  (while (< ti (sslength sst))
    (setq en (entget (ssname sst ti)))
    (setq en (subst (cons 50 gocrad) (assoc 50 en) en))
    (entmod en)
    (setq ti (1+ ti))
  )
  (princ)
  (princ)
)
;=======================================================
(defun c:cblay(/ ssb blist si bi Dtype i)
  (command ".UNDO" "BE")
  (setq ssb (ssget "_X" '((0 . "INSERT"))))
  (setq blist '() si 0)
  (while (< si (sslength ssb))
    (setq bi (ssname ssb si))
    (setq blist (append blist (list (list (cdr (assoc 2 (entget bi))) bi))))
    (setq si (1+ si))
  )
  (setq	Dtype '())
  (while blist
    (setq Dtype (append Dtype (list (car blist))))
    (setq blist (vl-remove-if '(lambda (x) (= (car x) (car (car blist)))) blist))
  )
  (setq i 0)
  (while (< i (length Dtype))
    (setq bi (cadr (nth i Dtype)))
    (ChangeSubLayer bi)
    (setq i (1+ i))
  )
  (command ".UNDO" "E")
  (command "regen" ^C^C)
  (princ)
  (princ)  
)
;=======================================================
(defun ChangeSubLayer (Ent / EntLst Layer Ename	EntLst SubEnt SubEntLst SubLayer)
  (setq EntLst (entget Ent))
  (if (equal "INSERT" (cdr (assoc 0 EntLst)))
    (progn
      (setq Layer (cdr (assoc 8 EntLst)))
      (setq Ename (tblobjname "block" (cdr (assoc 2 EntLst))))
      (setq EntLst (entget Ename))
      (setq SubEnt (entnext Ename))
      (while SubEnt
	(setq SubEntLst (entget SubEnt))
	(setq SubLayer (cdr (assoc 8 SubEntLst)))
	(if (/= Layer SubLayer)
	  (progn
	    (setq SubEntLst (subst (cons 8 Layer) (cons 8 SubLayer) SubEntLst))
	    (entmod SubEntLst)
	  )
	)
	(setq SubEnt (entnext SubEnt))
      )
    )
  )
  (princ)
)
;===========================================================================================================================================
(defun c:defkhung(/ path)
  (setq path (getvar "dwgprefix"))
  (setq drawings (getfiled "Ch\U+1ECDn b\U+1EA3n v\U+1EBD khung tên" path "dwg" 0))
  (princ)
  (princ)
)
;======================================================================================================================================================================
(defun chenkhung(pt / th thl i thi list_thi loai default old new tmode)
  (setq tmode (getvar "TILEMODE"))
  (If (= tmode 1) (Setvar "TILEMODE" 0))
  (setvar "INSUNITS" 4)
  (command "xref" "a" drawings pt 1 1 0)
  (command ".zoom" "e")
)
;======================================================================================================================================================================
(defun 2p2khung(pp1 pp2 delx dely sca /)
  (if (= quay "0")
    (progn
      (setq p0 pp1)
      (setq p1 (polar p0 (- (angle pp1 pp2) (* 0.5 pi)) (* sca 0.5 dely)))
      (setq p4 (polar p0 (+ (angle pp1 pp2) (* 0.5 pi)) (* 0.5 sca dely)))
      (setq p2 (polar p1 (angle pp1 pp2) (* sca delx)))
      (setq p3 (polar p4 (angle pp1 pp2) (* sca delx)))
      (setvar "OSMODE" 0.0)
      (command ".PLINE")
      (command p0)
      (command p1)
      (command p2)
      (command p3)
      (command p4)
      (command "c" ^C^C)
      (setvar "OSMODE" os)
      (setq ktam (entlast))
    )
    (progn
      (setq p0 pp1)
      (setq p1 (polar p0 (* -0.5 pi) (* sca 0.5 dely)))
      (setq p4 (polar p0 (* 0.5 pi) (* 0.5 sca dely)))
      (setq p2 (polar p1 0.0 (* sca delx)))
      (setq p3 (polar p4 0.0 (* sca delx)))
      (setvar "OSMODE" 0.0)
      (command ".PLINE")
      (command p0)
      (command p1)
      (command p2)
      (command p3)
      (command p4)
      (command "c" ^C^C)
      (setvar "OSMODE" os)
      (setq ktam (entlast))
    )
  )
)
;======================================================================================================================================================================
(defun xdt_b()
  (done_dialog)
  (setq xdt_var T)
)
;======================================================================================================================================================================
(defun QPnhat(/ tm s_len)
  (setq ss1 nil)
  (while (= ss1 nil)
    (terpri)(princ "\nCh\U+1ECDn \U+0111\U+01B0\U+1EDDng tim tuy\U+1EBFn: ")
    (SETQ SS1 (SSGET '((-4 . "<OR") (0 . "LWPOLYLINE") (0 . "POLYLINE")(-4 . "OR>"))))
  )
  (setq s_len (sslength ss1))
  (if (/= s_len 1) (c:nt))
  (setq tuyen (ssname ss1 0))
)
;======================================================================================================================================================================
(defun btna()
  (setq giaplai (get_tile "giaplai"))
  (if giaplai
    (setq giaplai (atof giaplai))
  )
  (done_dialog)
  (setq userclick T)
)
;======================================================================================================================================================================
(defun btnc()
  (done_dialog)
  (setq userclick nil)
)
;======================================================================================================================================================================
(defun tlz_t()
  (setq tlz (get_tile "tlz"))
  (if (/= tlz nil) (setq rai_tl (/ 2.00 (atoi tlz))))
)
;======================================================================================================================================================================
(defun quay_l()
  (setq quay (get_tile quay))
)
;======================================================================================================================================================================
(defun c:rai(/ f str DCL_ID num i)
  (setvar "INSUNITS" 4)
  (setq DCL_ID (load_dialog "rai.dcl"))
  (if (not (new_dialog "rai" DCL_ID)) (exit))
  (if giaplai (set_tile "giaplai" (rtos giaplai 2 2)))
  (setq quay (Get_tile "quay"))
  (if (or (= tlz nil) (= tlz "")) (setq tlz (Get_tile "tlz")) (set_tile "tlz" tlz))
  (if (/= tlz nil) (setq rai_tl (/ 2.00 (atoi tlz))))
  (if (and (/= goc nil) (/= tuyen nil)) (mode_tile "tuyen" 0))
  (action_tile "xdt" "(xdt_b)")
  (action_tile "tlz" "(tlz_t)")
  (action_tile "quay" "(quay_l)")
  (action_tile "accept" "(btna)")
  (action_tile "cancel" "(done_dialog) (setq userclick nil)")
  (start_dialog)
  (unload_dialog DCL_ID)
  (if (= xdt_var T)
    (progn
      (QPnhat)
      (setq xdt_var nil)
      (c:rai)  
    )
  ) 
  (if (= userclick T)
    (progn
      (bd_rai)
      (setq userclick nil)
    )
  )
)
;======================================================================================================================================================================
;BINH DO
;Ham chen vao cac mv de rai khung ban ve
(defun bd_rai(/ kword sslen i os cl s0 sslen s i_ename i_cat k d0 all all_len)
  (setq os (getvar "OSMODE"))
  (setq cl (getvar "CLAYER"))
  (command "-layer" "n" "mv" "")
  (command "-layer" "p" "n" "mv" "c" "8" "mv" ^C^C)
  (command "-layer" "s" "mv" "")
  (if (= drawings nil)
    (c:defkhung)
  )
  (setq delx 420.0
	dely 297.0
  )
  (setq pkhung (ssadd))
  (setq tm (vla-get-length (vlax-ename->vla-object tuyen)))
  (setq sca (/ 1 (atof tlz)))
  (setq sodiem (fix (+ 0.0 (/ tm (- (* sca delx) giaplai))))
	nsi 0)
  (setq vlat-tuyen (vlax-ename->vla-object tuyen))
  (while (< nsi sodiem)
    (setq l1 (* nsi (- (* sca delx) giaplai)))
    (setq l2 (* (1+ nsi) (- (* sca delx) giaplai)))
    (setq pp1 (vlax-curve-getpointatdist vlat-tuyen l1))
    (setq pp2 (vlax-curve-getpointatdist vlat-tuyen l2))
    (setq pkhung (ssadd (2p2khung pp1 pp2 delx dely sca) pkhung))
    (setq nsi (1+ nsi))
  )
  (setq l1 (* nsi (- (* sca delx) giaplai)))
  (setq l2 tm)
  (setq pp1 (vlax-curve-getpointatdist vlat-tuyen l1))
  (setq pp2 (car (reverse (OBJ2PLIST tuyen))))
  (setq pkhung (ssadd (2p2khung pp1 pp2 delx dely sca) pkhung))
  (setvar "CLAYER" cl)
)
;======================================================================================================================================================================
(defun c:raibd(/ sk k os cl all all_len i_ename i_cat i_tag d0 d1 d2 d3 d4 tm mv1 mv2)
  (setq os (getvar "OSMODE"))
  (SETVAR "OSMODE" 0)
  (setq cl (getvar "CLAYER"))
  (command "-layer" "n" "mv" "")
  (command "-layer" "p" "n" "mv" "c" "8" "mv" ^C^C)
  (command "-layer" "s" "mv" "")  
  (setq sk 0)
  (while (< sk (sslength pkhung))
    (setq kki (ssname pkhung sk))
    (setq pliss (OBJ2plist kki))
    (if (= (length pliss) 5)
      (setq d0 (nth 0 pliss)
	    d1 (nth 1 pliss)
	    d2 (nth 2 pliss)
	    d3 (nth 3 pliss)
	    d4 (nth 4 pliss)
      )
    )
    (setq tm (getvar "TILEMODE"))
    (if (= tm 1) (setvar "TILEMODE" 0))
    (setq pt (list (* sk 500) 0))
    (setq
      mv1 (list (+ (car pt) 27.0) (+ (cadr pt) 41.0))
      mv2 (list (+ (car pt) 407.0) (+ (cadr pt) 286.0))
    )
    (chenkhung pt)
    (command ".mview" mv1 mv2 "")
    (command ".mspace")
    (command ".ucs" "w")
    (command ".ucs" "n" "3p" d1 d2 d4)
    (command ".plan" "" "")
    (command ".ucs" "w")
    (command ".zoom" "w" d1 d3)
    (setq zoom (strcat tlz "xp"))
    (command ".zoom" zoom)    
    (command ".pspace")
    (setq sk (+ sk 1))
  )
  (setvar "TILEMODE" 1)
  (COMMAND ".ERASE" pkhung "")
  (setvar "TILEMODE" 0)
  (setvar "OSMODE" OS)
  (setvar "CLAYER" cl)
)
;=====================================================================================================================================================================
(defun obj2plist(obj-ename / en timp timl pli)
  (if (= (cdr (assoc 0 (entget obj-ename))) "LINE")
    (progn
      (setq timp (list
		   (cdr (assoc 10 (entget obj-ename)))
		   (cdr (assoc 11 (entget obj-ename)))
		 )
      )
    )
  )
  (if (= (cdr (assoc 0 (entget obj-ename))) "POLYLINE")
    (progn
      (setq en obj-ename)
      (while (/= (cdr (assoc 0 (entget en))) "SEQEND")
	(if (= (cdr (assoc 0 (entget en))) "VERTEX")
	  (setq timp (append timp (list (cdr (assoc 10 (entget en))))))
	)
	(setq en (entnext en))
      )
    )
  )
  (if (= (cdr (assoc 0 (entget obj-ename))) "LWPOLYLINE")
   (progn
      (setq timl (entget obj-ename))
      (setq pli 0)
      (while (< pli (length timl))
	(if (= (car (nth pli timl)) 10)
	  (setq timp (append timp (list (cdr (nth pli timl)))))
	)
	(setq pli (1+ pli))
      )
    )
  )
  timp
)
(princ)
(princ)

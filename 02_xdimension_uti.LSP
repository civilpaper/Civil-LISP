(defun DXF (code elist)
  (cdr (assoc code elist))
  )
;;;;;;;;;;;;;;;;;;;;;;;;;;;;;;;;;;;;;;;;;;;;;;;;;;;;;;;;;;;;;;;;;;;;;;;;;
(defun c:DUP(/ tm sslen vp sset ssl ed old new temp)
  (if (= ly_scale nil) (c:tl))
  (setq zoom_xp (/ 1 ly_scale))
  (setq dimst (getvar "DIMSTYLE"))
  (command ".dimstyle" "r" "xStandard" "")
  (setvar "DIMSCALE" ly_scale)
  (command ".dimstyle" "s" (strcat "Zoom" (rtos zoom_xp 2 2) "Xp") "" ^C ^C)
  (setvar "TILEMODE" 1)
  (setq sset (ssget '((0 . "DIMENSION"))))
  (setq ssl (sslength sset))
  (while (> ssl 0)
    (progn
      (setq temp (ssname sset (setq ssl (1- ssl))))
      (setq ed (entget temp))
      (setq old (cons 3 (DXF 3 ed)))
      (setq new (cons 3 (strcat "Zoom" (rtos zoom_xp 2 2) "Xp")))
      (setq ed (subst new old ed))
      (entmod ed)
    )
  )
 (princ)
  (command ".dimstyle" "r" "xStandard" "")
)

(prompt "\n\nL O A D I N G    D I M _ U T I . L S P")

(defun DXF (code elist)
  (cdr (assoc code elist))
)

(defun CDXF (tt elist)
  (car (nth tt elist))
)
;CDXF - xac dinh thu tu cua danh sach

(defun xdtt (code elist)
(setq i 0)
(while (/= code (cdxf i elist))
;(progn
  (setq i (+ 1 i))
);while
)


;;;;;;;;;;;;;;;;;;;;;;;;;;;;;;;;;;;;;;;;
(defun DIM_u_ssget ( / ssl  nsset temp ed )
  (setq sset (ssget))
  (setq ssl (sslength sset) 
        nsset (ssadd)
  )
  (print ssl)
  (princ "entities found. ")  
  (princ "\nVerifying the selected entities -- please wait. ")
  (while (> ssl 0)
    (progn
      (setq temp (ssname sset (setq ssl (1- ssl))))
      (setq ed (entget temp))
      (if (= (DXF 0 ed) "DIMENSION") (ssadd temp nsset))
    )
  )
  (setq ssl (sslength nsset)
        sset nsset
  )
  (print ssl)
  (princ "DIMENSION entities found. ")
  (princ)
  (print)
);defun u_ssget

;;;;;;;;;;;;;;;;;;;;;;;;;;;;;;;;;;;;;;;;;;;;;;;;;;;;;;;
(prompt "\n		D2  : To change DIMENSION entities to layer 2")
(princ)

(defun c:D2( / sset ssl temp ed old new )
(dim_u_ssget)
;(setq la (getstring "New layer of selected dimension entities : "))
(setq la "2")
(setq ssl (sslength sset))
  (while (> ssl 0)
    (progn
      (setq temp (ssname sset (setq ssl (1- ssl))))
      (setq ed (entget temp))

       (setq old (cons 8 (DXF 8 ed))
             new (cons 8 la)
             ed (subst new old ed)
           )
      (entmod ed)  
      )  
  )

 (princ)
);defun
;;;;;;;;;;;;;;;;;;;;;;;;;;;;;;;;;;;;;;;;;;;;;;;;;;;;;;;
(prompt "\n		DL  : To change DIMENSION entities to a specific layer")
(princ)

(defun c:DL( / sset ssl temp ed old new )
(dim_u_ssget)
(setq la (getstring "New layer of selected dimension entities : "))
(setq ssl (sslength sset))
  (while (> ssl 0)
    (progn
      (setq temp (ssname sset (setq ssl (1- ssl))))
      (setq ed (entget temp))

       (setq old (cons 8 (DXF 8 ed))
             new (cons 8 la)
             ed (subst new old ed)
           )
      (entmod ed)  
      )  
  )

 (princ)
);defun

;;;;;;;;;;;;;;;;;;;;;;;;;;;;;;;;;;;;;;;;;;;;;;;;;;;;;;;
(prompt "\n		DH  : To change DIMENSION entities to the default text locations.")
(princ)

(defun c:DH()
  (command "dimedit" "Home" )
  (princ)
);defun
;=================
;(defun c:DH(/ sset ssl temp ed old new )
;(dim_u_ssget)
;(setq la (getstring "New layer of selected dimension entities : "))
;(setq ssl (sslength sset))
;  (while (> ssl 0)
;    (progn
;      (setq temp (ssname sset (setq ssl (1- ssl))))
;      (setq ed (entget temp))

;       (setq old (cons 70 (DXF 70 ed))
;             new (cons 70 32)
;             ed (subst new old ed)
;           )
;      (entmod ed)  
;      ;(entupd ed)  
;      )  
;  )

; (princ)
;);defun
;;;;;;;;;;;;;;;;;;;;;;;;;;;;;;;;;;;;;;;;;;;;;;;;;;;;;;;
(prompt "\n		MD  : To mirror TEXT of DIMENSION entities.")
(princ)

(defun c:MD( / sset ssl temp ed old new )
(dim_u_ssget)
;(setq la (getstring "New layer of selected dimension entities : "))
(setq ssl (sslength sset))
  (while (> ssl 0)
    (progn
      (setq temp (ssname sset (setq ssl (1- ssl))))
      (setq ed (entget temp))

       (setq old (cons 51 (DXF 51 ed))
             new (cons 51 3.14159)
             ed (subst new old ed)
           )
      (entmod ed)  
      )  
  )

 (princ)
);defun
;;;;;;;;;;;;;;;;;;;;;;;;;;;;;;;;;;;;;;;;;;;;;;;;;;;;;;;
;-----------------------------------------------------------------
(prompt "\n		H   : to use new horizontal dim method")
(defun c:H ( )
  (prompt "\nNew dim method. ")
;  (command "LAYER" "N" "Laydim" "C" "2" "Laydim" "")
;  (command "LAYER" "S" "Laydim" "")
  (setq pt1 (getpoint "\nSelect first extension line origin : ")
        pt2 (getpoint "\nSelect second extension line origin : " pt1) 
  )
  (if (= (car pt1) (car pt2)) 
      (VER pt1 pt2)
      (HOR pt1 pt2) 
  )
)
;-----------------------------------------------------------------
(prompt "\n		V   : to use new vertical dim method")
(defun c:V()
  (prompt "\nNew dim method. ")
;  (command "LAYER" "N" "Laydim" "C" "2" "Laydim" "")
;  (command "LAYER" "S" "Laydim" "")
  (setq OS (getvar "OSMODE"))
  (setq pt1 (getpoint "\nSelect first extension line origin : ")
             pt2 (getpoint "\nSelect second extension line origin : " pt1) 
  ) 
 (if (= (cadr pt1) (cadr pt2)) 
      (HOR pt1 pt2)
      (VER pt1 pt2) 
  )
)
;-----------------------------------------------------------------
(defun HOR ( pt1 pt2 )
  (setq #DIM 1)
  (setq OS (getvar "OSMODE"))
  (setvar "OSMODE" 0)
  (setq #pt3 (getpoint "\nExtension line origin location :")
        pt11 (list (car pt1) (cadr #pt3))
        pt22 (list (car pt2) (cadr #pt3))
  )
  (command "DIM1" "HOR" pt11 pt22)
  (setvar "OSMODE" OS) 
)
;-----------------------------------------------------------------
(defun VER ( pt1 pt2 )
  (setq OS (getvar "OSMODE"))
  (setq #DIM 2)
  (setvar "OSMODE" 0) 
  (setq #pt3 (getpoint "\nExtension line origin location :")
        pt11 (list (car #pt3) (cadr pt1))
        pt22 (list (car #pt3) (cadr pt2))
  )
  (command "DIM1" "VER" pt11 pt22)
  (setvar "OSMODE" OS) 
)
;-----------------------------------------------------------------

(prompt "\n		CON : to use new continuos dim method")
(defun c:con( / pt1 pt11 pt4 pt5 A dis pt11 pt22)
 (setq OS (getvar "OSMODE"))
 (if (= #DIM 1)
   (progn
      (prompt "\nNew dim method.")
      (setq pt1 (getpoint "\nSelect next extension line origin : ")
            pt11 (list (car pt1) (cadr #pt3))
      )
      (setvar "OSMODE" 0) 
      (command "DIM1" "CON" pt11)
   )
 )
 (if (= #DIM 2)
   (progn
     (prompt "\nNew dim method. ")
     (setq pt1 (getpoint "\nSelect next extension line origin : ")
           pt11 (list (car #pt3) (cadr pt1))
     )
     (setvar "OSMODE" 0) 
     (command "DIM1" "CON" pt11)
   )
 )
 (if (= #DIM 3)
   (progn
     (prompt "\nNew dim method. ")
     (setq pt1 (getpoint "\nSelect next extension line origin : ")
           pt2 (polar #pt22 #A 100)
           pt3 (polar pt1 (+ #A 1.570796) 100)
           pt5 (inters #pt22 pt2 pt1 pt3 seg)
     )
     (setvar "OSMODE" 0) 
     (command "dim1" "con" pt5)
   )
 )
 (setvar "OSMODE" OS) 
)
;-----------------------------------------------------------------

(defun c:ali()
(command "dim1" "ali"))
;----------------------------------------------------------------------------------------------------------
(defun c:ob()
(command "dim" "oblique"))
;-----------------------------------------------------------------
; more.lsp collected and modified by Nobody in August, 2006
(princ "\n\		H1  : canh le vi tri cua cac dimension ngang")
(princ "\n\		H2  : canh le diem dong cua cac dimension ngang")
(princ "\n\		V1  : canh le vi tri cua cac dimension doc")
(princ "\n\		V2  : canh le diem dong cua cac dimension doc")
;-------------------------------------------------------------------
(DEFUN C:v1 ()
 (SETQ CMD (GETVAR "CMDECHO"))
 (SETVAR "CMDECHO" 0)
 (COMMAND "UCS" "W")
 (SETVAR "CMDECHO" 1)
 (PROMPT"\nSelect dimension(s) to be aligned")
 (SETQ SET (SSGET))
 (PROMPT"\nSelect new dimension position")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L10 (ASSOC 10 A))
     (SETQ M10 (CDR L10))
     (SETQ L11 (ASSOC 11 A))
     (SETQ M11 (CDR L11))
     (SETQ P10 (LIST 10 X3 (CADR M10) (CADDR M10)))
     (SETQ A (SUBST P10 L10 A))
     (ENTMOD A)			
    )
   )
  (SETQ INDEX (+ INDEX 1))
 )
 (SETVAR "CMDECHO" 0)
 (COMMAND "UCS" "P")
 (SETVAR "CMDECHO" CMD)
)
;----------------------------------------------------------------------------------------------

(DEFUN C:v2 ()
 (SETQ CMD (GETVAR "CMDECHO"))
 (SETVAR "CMDECHO" 0)
 (COMMAND "UCS" "W")
 (SETVAR "CMDECHO" 1)
 (PROMPT"\nSelect vertical dimension(s) extensions to be aligned")
 (SETQ SET (SSGET))
 (PROMPT"\nSelect new extension position")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 X3 (CADR M13) (CADDR M13)))
     (SETQ P14 (LIST 14 X3 (CADR M14) (CADDR M14)))
     (SETQ A (SUBST P13 L13 A))
     (SETQ A (SUBST P14 L14 A))
     (ENTMOD A)			
    )
   )
  (SETQ INDEX (+ INDEX 1))
 )
 (SETVAR "CMDECHO" 0)
 (COMMAND "UCS" "P")
 (SETVAR "CMDECHO" CMD)
 (PRINC)
)

;;--------------------------------------------------------------------------------------------------------------

(DEFUN C:h1 ()
 (SETQ CMD (GETVAR "CMDECHO"))
 (SETVAR "CMDECHO" 0)
 (COMMAND "UCS" "W")
 (SETVAR "CMDECHO" 1)
 (PROMPT"\nSelect dimension(s) to be aligned")
 (SETQ SET (SSGET))
 (PROMPT"\nSelect new dimension position")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L10 (ASSOC 10 A))
     (SETQ M10 (CDR L10))
     (SETQ P10 (LIST 10 (CAR M10) Y3 (CADDR M10)))
     (SETQ A (SUBST P10 L10 A))
     (ENTMOD A)			
    )
   )
  (SETQ INDEX (+ INDEX 1))
 )
 (SETVAR "CMDECHO" 0)
 (COMMAND "UCS" "P")
 (SETVAR "CMDECHO" CMD)
)

;;---------------------------------------------------------------------------------------------------------------------

(DEFUN C:h2 ()
 (SETQ CMD (GETVAR "CMDECHO"))
 (SETVAR "CMDECHO" 0)
 (COMMAND "UCS" "W")
 (SETVAR "CMDECHO" 1)
 (PROMPT"\nSelect dimension(s) to be aligned")
 (SETQ SET (SSGET))
 (PROMPT"\nSelect new dimension position")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 (CAR M13) Y3 (CADDR M13)))
     (SETQ T13 (CDR P13))
     (SETQ P14 (LIST 14 (CAR M14) Y3 (CADDR M14)))
     (SETQ A (SUBST P13 L13 A))
     (SETQ A (SUBST P14 L14 A))
     (ENTMOD A)			
    )
   )
  (SETQ INDEX (+ INDEX 1))
 )
 (SETVAR "CMDECHO" 0)
 (COMMAND "UCS" "P")
 (SETVAR "CMDECHO" CMD)
)
	 
;;;;;;;;;;;;;;;;;;;;;;;;;;;;;;;;;;;;;;;;;;;;;;;;;;;;;;;

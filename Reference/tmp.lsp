;;;;;;;;;;;;;;;;;;;;;;;;;;;;;;;;;;;;;;;;;;;;;;;;;;;;;;;;;;;;;;;;;;;;;;;;;;;;;;;;;;;;;;;;;
(Defun matsosanh(/ pt cao)
  (prompt "\nKhai báo M\U+1EB7t So Sánh")
  (setq pt (getpoint "\nChi mot diem co cao do la 16.5 "))
  (setq #mss (- (cadr pt) 16.5))
)
(defun c:#mss() (matsosanh))
;;;;;;;;;;;;;;;;;;;;;;;;;;;;;;;;;;;;;;;;;;;;;;;;;;;;;;;
(defun c:elevation(/ ss unit cl dz ot pt ptside ang y)
  (matsosanh)
  (setq ss (ssadd))
  (setq unit (getvar "INSUNITS"))
  (setvar "INSUNITS" 4)
  (if (= #Bacc nil) (setq #Bacc (getint "\nPh\U+1EA7n th\U+1EADp phân: ")))
  (setq CL (getvar "clayer"))
  (setvar "CLAYER" "0") 	
  (setq DZ (getvar "DIMZIN"))
  (setvar "DIMZIN" 0)
  (setq OT (getvar "ORTHOMODE"))
  (setvar "ORTHOMODE" 0)
  (setq pt (getpoint "\n\U+0110i\U+1EC3m l\U+1EA5y Cao \U+0111\U+1ED9: ")
	ptside (getpoint "\nH\U+01B0\U+1EDBng: " pt)
	ang (angle pt ptside)
  )
  (setq y (- (cadr pt) #mss))
  (cond
    ((> y 0) (setq y (strcat "+" (rtos y 2 #Bacc))))
    ((< y 0) (setq y (rtos y 2 #Bacc)))
    ((= y 0) (setq y "%%p0.00"))
    )
  (setq y (ustr 0 "\nCao \U+0111\U+1ED9 \U+0110i\U+1EC3m là: " y T))
  (if (AND (>= ang 0) (< ang 1.5708)) (command ".INSERT" "Elevation" pt ly_scale ly_scale "0" y))
     ( if	 (AND (>= ang 1.5708) (< ang 3.1416)) (command ".INSERT" "Elevation3" pt ly_scale ly_scale "0" y))
     ( if	 (AND (>= ang 3.1416) (< ang 4.7124)) (command ".INSERT" "Elevation2" pt ly_scale ly_scale "0" y))
     ( if	 (AND (>= ang 4.7124) (< ang 6.2832)) (command ".INSERT" "Elevation1" pt ly_scale ly_scale "0" y))
  (setq ss (ssadd (entlast) ss))
  (bup ss)
  (setvar "DIMZIN" DZ)
  (setvar "ORTHOMODE" OT)
  (setvar "CLAYER" CL)
  (setvar "INSUNITS" unit)
)
(defun c:ev() (c:elevation))

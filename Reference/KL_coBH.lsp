(defun c:QQ1()
  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "GRAVEL" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)

;;; (command "erase" ss "")

  (setq ss nil)
  (command "redraw")
  (setq dtl (/ dtl tl2))
;;(setq dtl (/ dtl 2.0))
  (prompt (strcat "\nTotal area : " (rtos dtl 2 2)))
  (PRINT)
  (setq en (car (entsel "Thay cho so : ")))
  (setq elst (entget en))
  (setq elst (subst (cons 1 (rtos dtl 2 2)) (assoc 1 elst) elst))
  (entmod elst)
  (command "change" en "" "p" "layer"  7 "" "")  
;  (print)
;  (prompt (strcat "\nTotal area : " (rtos dtl 2 2)))
;  (print)
;  (setq pt2 (getpoint "\nPoint to write: "))
;  (command "text" pt2  "0" "2" (rtos dtl 4 2))
);defun

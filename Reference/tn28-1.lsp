(PROMpT "\n Loading Tn28.lsp by CHIEN HUY " ) 
(PROMpT "\n tL2: thay doi ty le ban ve " ) 
;------------------------------------------------------------------


(defun C:tl2 ()
    (initget (+ 1 2 4))
    (print)
    (print)
    (setq Ty_le (getreal "\nTy le : "))
)
;------------------------------------------------------------------
(prompt "\n DB: ve duong bao va tinh khoi luong")
(defun C:DB ()

  (if (= Ty_le nil)
    (progn
    (initget (+ 1 2 4))
    (print)
    (print)
    (setq Ty_le (getreal "\nTy le : "))
   )
  )
  (setq he_so (/ 1000.0 Ty_le))
  (setq he_so2 (* he_so he_so))
  (print)
  (setq eclast (getvar "CMDECHO"))
  (setq lalast (getvar "CLAYER"))
  (setq oslast (getvar "OSMODE"))
  (setvar "CMDECHO" 0)
  (setvar "OSMODE" 0)
  (command "-layer" "s" 7 "")
  (setq i "1 : " c 1.0)
  (setq s 0)
  (repeat 2
    (print)
    (setq e (entget (car (entsel (strcat "Taluy" i) ))))
    (if (/= e nil) (progn
    (setq pt1 (cdr (assoc 10  e)) pt2 (cdr (assoc 11 e)))
    (setq x1 (car pt1)  y1  (cadr pt1))
    (setq x2 (car pt2)  y2  (cadr pt2))

    (if (< y2  y1)  (progn
      (setq  x7 x1  y7 y1)
      (setq  x1 x2  y1 y2)
      (setq  x2 x7  y2 y7) 
                     ))
    (setq els (entget (car (entsel "Gioi han " ))))
    (setq pt3 (cdr (assoc 10 els)) pt4 (cdr (assoc 11 els)))
    (setq x3 (car pt3)  y3  (cadr pt3))
    (setq x4 (car pt4)  y4  (cadr pt4))

    (if (< y4  y3)  (progn
      (setq  x7 x3  y7 y3)
      (setq  x3 x4  y3 y4)
      (setq  x4 x7  y4 y7) 
                    ))
      
      (setq x7  (+ x1 (* c  11.18)))
      (setq x8 (+ x7 (* c  4)) y8 (+ y1 2))
      (setq x9 (+ x3 (* c  100)) y9 (+ y3 2))

      (setq pt6 (inters (list x7 y1) (list x8 y8)  (list x3 y3) (list x4  y4) nil ))
      (setq x6 (car pt6)  y6  (cadr pt6))
   
      (command "line" (list x7 y1) pt6 "" )
     
     (setq s1 11.18)
     (setq s1 (* (/ s1 he_so2) (- y3 y1))) 
     (setq s (+ s s1))
      ))
    (setq i "2 :"  c  -1.0) 
      )
  (print s)
 
  (setq en (car (entsel "Thay so dat dap bao : ")))
  (setq elst (entget en))
  (setq chso1 (cdr (assoc 1 elst)))
  (setq so1 (atof (substr chso1 1)))
  (setq elst (subst (cons 1  (rtos s 2 2)) (assoc 1 elst) elst)) 
  (entmod elst)
  (setq en2 (car (entsel "\n dap cat: ")))
  (setq elst2 (entget en2))
  (setq chso2 (cdr (assoc 1 elst2)))
  (setq so2 (atof (substr chso2 1)))
  (setq so2 (+ so2 (- s so1)))
  (setq elst2 (subst (cons 1 (rtos so2 2 2)) (assoc 1 elst2) elst2))
  (entmod elst2)
  (command "change" en en2 "" "p" "layer"  6 "" "")  
  (setvar "OSMODE" oslast)
  (setvar "CLAYER" lalast)
  (setvar "CMDECHO" eclast)
)


(prompt "\n sq: tinh sua kl datbao")
(defun c:sq()

  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en (car (entsel "Thay cho so 1 : ")))
  (setq elst (entget en))
  (setq chso1 (cdr (assoc 1 elst)))
  (setq so1 (atof (substr chso1 1)))
  (setq elst (subst (cons 1 (rtos dtl 2 2)) (assoc 1 elst) elst))
  (entmod elst)
  (command "change" en "" "p" "layer"  7 "" "")  
    (setq en2 (car (entsel "\n Thay cho so 2: ")))
    (setq elst2 (entget en2))
    (setq chso2 (cdr (assoc 1 elst2)))
    (setq so2 (atof (substr chso2 1)))
    (setq so2 (- so2 (- dtl so1)))
    (setq elst2 (subst (cons 1 (rtos so2 2 2)) (assoc 1 elst2) elst2))
  (entmod elst2)
  
  
  (command "change"  en2 "" "p" "layer"  7 "" "")  
;  (print)
;  (prompt (strcat "\nTotal area : " (rtos dtl 2 2)))
;  (print)
;  (setq pt2 (getpoint "\nPoint to write: "))
;  (command "text" pt2  "0" "2" (rtos dtl 4 2))
);defun



(prompt "\n ww: ve duong bao ben phai")
(defun C:ww ()
  (if (= Ty_le nil)
    (progn
    (initget (+ 1 2 4))
    (print)
    (print)
    (setq Ty_le (getreal "\nTy le : "))
   )
  )
  (setq he_so (/ 1000.0 Ty_le))
  (setq he_so2 (* he_so he_so))
  (print)
  (setq eclast (getvar "CMDECHO"))
  (setq lalast (getvar "CLAYER"))
  (setq oslast (getvar "OSMODE"))
  (setvar "CMDECHO" 0)
  (setvar "OSMODE" 0)
  (command "-layer" "s" 7 "")
  (setq s 0)
  (setq c -1)
    (setq e (entget (car (entsel "Taluy phai" ))))
    (if (/= e nil) (progn
    (setq pt1 (cdr (assoc 10  e)) pt2 (cdr (assoc 11 e)))
    (setq x1 (car pt1)  y1  (cadr pt1))
    (setq x2 (car pt2)  y2  (cadr pt2))

    (if (< y2  y1)  (progn
      (setq  x7 x1  y7 y1)
      (setq  x1 x2  y1 y2)
      (setq  x2 x7  y2 y7) 
                     ))
    (setq els (entget (car (entsel "Gioi han " ))))
    (setq pt3 (cdr (assoc 10 els)) pt4 (cdr (assoc 11 els)))
    (setq x3 (car pt3)  y3  (cadr pt3))
    (setq x4 (car pt4)  y4  (cadr pt4))

    (if (< y4  y3)  (progn
      (setq  x7 x3  y7 y3)
      (setq  x3 x4  y3 y4)
      (setq  x4 x7  y4 y7) 
                    ))
      
      (setq x7  (+ x1 (* c  11.18)))
      (setq x8 (+ x7 (* c  4)) y8 (+ y1 2))
      (setq x9 (+ x3 (* c  100)) y9 (+ y3 2))

      (setq pt6 (inters (list x7 y1) (list x8 y8)  (list x3 y3) (list x9  y9) nil ))
      (setq x6 (car pt6)  y6  (cadr pt6))
   
      (command "line" (list (+ x1 (* c 11.18)) y1) (list x6 y6) "" )
     
     (setq s1 (/   (* c (- x6 x3))  2 ))
     (setq s1 (* (/ s1 he_so2) (- y3 y1))) 
     (setq s (+ s s1))

     ))

  (print s)

   (setq en (car (entsel "Thay so dat dap bao : ")))
   (setq elst (entget en))
   (setq elst (subst (cons 1  (rtos s 2 2)) (assoc 1 elst) elst)) 
   (entmod elst)
   (command "change" en "" "p" "layer" 6 "" "")  
  (setvar "OSMODE" oslast)
  (setvar "CLAYER" lalast)
  (setvar "CMDECHO" eclast)
)
  (prompt "\n HC: ve & tinh khoi luong dao huu co, h= 0.3m ")
(defun C:HC ()
 
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.3))
  (command "layer" "s" "1" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
    (command "line" (list x1 y1) (list x2 y2) "")
    (setq pt1 pt2)
    (setvar "OSMODE" 33)
    (setq pt2 (getpoint "To : "))
  )
       ))
  (setq dthc (/ (/ dthc he_so2) 1))
  (setq en (car (entsel "Thay so dao dat huu co: ")))
  (setq elst (entget en))
  (setq elst (subst (cons 1  (rtos dthc 2 2)) (assoc 1 elst) elst))
  (entmod elst)
  (setq dtatb 0.00)
  (setvar "CLAYER" lalast)
 ;;(command "mm" "")
)
;;...................................................................

(prompt "\n VB: ve duong vet bun chieu sau 1.0m")
(defun C:VB ()
 
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sx he_so)
  (setq sy he_so)
  (setvar "OSMODE" 33)
  (command "-layer" "s" 1 "")
  (setq dy (* 1.0 sy))
  (setq pt1 (getpoint "\nDiem bat dau ben trai: "))
      (if (/= pt1 nil) (progn
   (setq pt2 (getpoint "diem cuoi : "))
    (if (/= pt2 nil) (progn
    (setq y1 (- (cadr pt1) dy) x1 (car pt1))
    (setq x2 (car pt2) y2 (cadr pt2))
    (setq ptl (getpoint "\n Chan taluy: "))
    (setq y1 (- y1 (* 0.02 (- x1 (car ptl)))))
    (setq x1 (car ptl))
    (setq pt1 (list x1 y1))
    (setq pt3 (list (- x1 2) (+ y1 2) ))
    (setq pt4 (list (- x2 2)  (- y2 2)))
    (setq els (entget (car (entsel "Gioi han 1:"))))
    (setq pt5 (cdr (assoc 10 els)) pt6 (cdr (assoc 11 els)))
    (setq pt7 (inters pt1 pt3  pt5 pt6 nil))
    (setq pt8 (inters pt2 pt4 pt1 (list (+ x1 100) (+ y1 2)) nil ))
    (setvar "OSMODE" 0)
    (command "line" pt7 pt1 pt8 pt2  "")
    (setq pt1 pt2)
       ))
  ))
  (setvar "OSMODE" 33)
  (setq pt1 (getpoint "\nDiem bat dau ben phai: "))
      (if (/= pt1 nil) (progn
    (setq pt2 (getpoint "To : "))
    (if (/= pt2 nil) (progn
    (setq y1 (- (cadr pt1) dy) x1 (car pt1))
    (setq x2 (car pt2) y2 (cadr pt2))
    (setq ptl (getpoint "\n Chan taluy: "))
    (setq y1 (- y1 (* 0.02 (- (car ptl) x1) )))
    (setq x1 (car ptl))
    (setq pt1 (list x1 y1))
    (setq pt3 (list (+ x1 2) (+ y1 2) ))
    (setq pt4 (list (+ x2 2)  (- y2 2)))
    (setq els (entget (car (entsel "Gioi han 1:"))))
    (setq pt5 (cdr (assoc 10 els)) pt6 (cdr (assoc 11 els)))
    (setq pt7 (inters pt1 pt3  pt5 pt6 nil))
    (setq pt8 (inters pt2 pt4 pt1 (list (- x1 100) (+ y1 2)) nil))
    (setvar "OSMODE" 0)
    (command "line" pt7 pt1 pt8 pt2  "")
    (setq pt1 pt2)
       ))
  ))
  (setvar "OSMODE" oslast)
  (setvar "CLAYER" lalast)
  (setvar "CMDECHO" eclast)
)

(defun C:VB2 ()
  (if (= Ty_le nil)
    (progn
    (initget (+ 1 2 4))
    (print)
    (print)
    (setq Ty_le (getreal "\nTy le : "))
    )
  )
  (setq he_so (/ 1000.0 Ty_le))
  (print)

  (setq eclast (getvar "CMDECHO"))
  (setq lalast (getvar "CLAYER"))
  (setq oslast (getvar "OSMODE"))
  (setvar "CMDECHO" 0)
  (setq sx he_so)
  (setq sy he_so)
  (setvar "OSMODE" 33)
  (setq Dvb (* 0.60 sy))
  (setq ptd  (getpoint "From <end of> : "))
  (initget (+ 1 4))
  (setq xd (car ptd) yd (cadr ptd))
  (print)
  (setq ptc (getpoint "To <end of> : "))
  (setq xc (car ptc) yc (cadr ptc))
  (setq yvb (- (min yd yc) Dvb))
  (if (> xc xd) (setq dx 30.0) (setq dx -30.0))
  (setq x1 (- xd dx) y1 (+ yvb 15.0))
  (setq x2 (+ xc dx) y2 (+ yvb 15.0))
  (setq pt1 (list x1 y1) ptd (list xd yvb) ptc (list xc yvb) pt2 (list x2 y2))
  (command "-layer" "s" "THKE" "")
  (setvar "OSMODE" 0)
  (command "line" pt1 ptd ptc pt2 "")
  (setvar "OSMODE" oslast)
  (setvar "CLAYER" lalast)
  (setvar "CMDECHO" eclast)
)
 (prompt "\n : GH ghi cao do trong MCN")
(defun C:GH ()

  (vmon)
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sy he_so)
  (command "layer" "s" 0 "")
  (setvar "osmode" 512)
  (print)
  (print)
  (setq pt (getpoint "\nDiem goc toa do <nearest to> : "))
  (setq yo (cadr pt))
  (setq y2 (- yo 10))
  (setq y1 (- y2 5))
  (setq y3 (+ y2 9))
  (setvar "osmode" 1)
  (setq pt (getpoint "\nDiem chuan <end of)        : ") )
  (setq yc (cadr pt))
 
      (setq en1 (car (entsel "Chon so cao do: ")))
      (setq elst1 (entget en1))
      (setq chso1 (cdr (assoc 1 elst1)))
      (setq hc (atof (substr chso1 1)))     
   
  (setq dy (- (* sy hc) yc))
  (print)
  (print)
  (setvar "osmode" 33)
  (setq pt (getpoint "\nDiem : "))
  (while (/= pt nil)
    (setq x (car pt) y (cadr pt))
    (setq h (/ (+ y dy) sy))
    (setq x1 (+ x 1))
    (setvar  "osmode" 0)
    (command "line" (list x y1) (list x y2) "")
    (command "text" "r" (list x y3) 1.8 90 (rtos h 2 2))
    (command "layer" "s" 6 "")
    (command "line" (list x yo) (list x y) "")
    (setvar "osmode" 33)
    (setvar "CLAYER" lalast)
    (print)
    (print)
    (setq pt (getpoint "\nDiem : "))
  )
  (setvar "OSMODE" oslast)
  (setvar "CLAYER" lalast)
  (setvar "CMDECHO" eclast)

  ;;(setvar "OSMODE" 0)
)
;*
;*

 (prompt "\n GL: ghi chieu dai")
(defun C:GL ()

  (if (= Ty_le nil)
    (progn
    (initget (+ 1 2 4))
    (print)
    (print)
    (setq Ty_le (getreal "\nTy le : "))
    )
  )
  (setq he_so (/ 1000.0 Ty_le))
  (print)

  (setq eclast (getvar "CMDECHO"))
  (setq lalast (getvar "CLAYER"))
  (setq oslast (getvar "OSMODE"))
  (setvar "CMDECHO" 0)
  (setq sx he_so)
  (setq lmin4 (/ 5.0 sx))	
  (setq lmin3 (/ 4.0 sx))
  (setq lmin1 (/ 1.5 sx))
  (command "layer" "s" 0 "")
  (command "osnap" "nearest")
  (print)
  (print)
  (setq pt (osnap (getpoint "\nNoi ghi cu ly <nearest to> : ") "nearest"))
  (setq y1 (cadr pt))
  (setq y2 (+ y1 5.0))
  (setq yc (+ y1 2.5))
  (print)
  (print)
  (setvar "OSMODE" 33)
  (setq pt (getpoint "\nTu diem <end,intersection of> : "))
  (while (/= pt nil)
    (setq x1 (car pt))
    (setq pt (getpoint "  Den diem <end,intersection of> : "))
    (setvar "OSMODE" 0)
    (setq x2 (car pt))
    (if (< x2 x1) (progn
      (setq xg x2)
      (setq x2 x1)
      (setq x1 xg)
      )
    )
    (setq dx (- x2 x1))
    (setq xt (/ dx sx))
    (setq sxt (rtos xt 2 2))
    (if (> xt 0.1) (progn
      ;;(setq kt " ")
      ;(while (= kt " ")
      ; (setq kk (substr sxt 1 1))
      ;  (if (= kk " ") (setq sxt (substr sxt 2)))
      ; (setq kt kk)
      ; )
      ;(setq len (strlen sxt))
      ;(setq kt (substr sxt len 1))
      ;;(while (= kt "0")
      ;;  (setq len (- len 1))
      ;;  (setq sxt (substr sxt 1 len))
      ;;  (setq kt (substr sxt len 1))
      ;;)
      ;;(if (= kt ".") (progn
      ;;  (setq len (- len 1))
      ;;  (setq sxt (substr sxt 1 len))
      ;;  )
      ;;)
      (setq len (strlen sxt))
      (setq xg (/ (+ x1 x2) 2.0))
      (setq x1 (+ x1 0.5))
      (setq x2 (- x2 0.5))
      (setq len1 -1)
      (if (> len 3) (setq len1 1))
      (if (= len 2) (setq len1 1))
      (if (> len1 0) (progn

      (if (< xt lmin3) (command "text"  "m" (list xg (+ yc 0) )  1.5  90  sxt)
        (command "text" "m" (list xg yc) 1.8 0 sxt)
        )

                      )
      )
      (if (= len 3) (progn
        (if (< xt lmin3) (command "text" "m" (list xg (+ yc 0) ) 1.5  90  sxt)
        (command "text" "m" (list xg yc) 2 0 sxt)
        )
        )
      )
      (if (= len 1) (progn
        (if (< xt lmin1) (command "text" "f" (list x1 yc) (list x2 yc) 2 sxt)
        (command "text" "m" (list xg yc) 2 0 sxt)
        )
        )
      )
      )
    )
    (setvar "OSMODE" 33)
    (print)
    (print)
    (setq pt (getpoint "\nTu diem <end of> : "))
  )
  (setvar "OSMODE" oslast)
  (setvar "CLAYER" lalast)
  (setvar "CMDECHO" eclast)
)
 (prompt "\n VV: tinh bu venh cac lop KCAD")
(defun C:vv ()
   
  (if (= Ty_le nil) (progn
    (setq Ty_le (getreal "\nDrawing scale : "))
                     )
 )
  (setq he_so (/ 1000 Ty_le))
  (setq he_so2 (* he_so he_so))
  (initget (+ 1  2  4))
 (setq lop (getint "n\lop: "))
 ;; (setq lop 2)
  (if (= lop 1) (setq Hmat (* 0.07 he_so)))
  (if (= lop 2) (setq Hmat (* 0.47
  he_so)))
  (if (= lop 3) (setq Hmat (* 0.62 he_so)))
;;(setq Hmat (* 0.05 he_so))
  (setq Hao (* 0.62 he_so))
  (setq lalast (getvar "CLAYER"))
  (setq oslast (getvar "OSMODE"))
  (setq settk (ssadd))
  (setq settn (ssadd))
  (setq ss (ssget))
  (setq c 0)
  (setq xmin 9000000 xmax -9000000)
  (setvar "OSMODE" 0)
  (while (< c (sslength ss))
    (setq en (ssname ss c))
    (setq elst (entget en))
    (setq loai (cdr (assoc 0 elst)))
    (if (= loai "LINE")
      (progn
        (setq pt1 (cdr (assoc 10 elst)) pt2 (cdr (assoc 11 elst)))
        (setq x1 (car pt1) x2 (car pt2))
        (if (> (abs (- x2 x1)) 0.001)
          (progn
            (setq la (cdr (assoc 8 elst)))
            (if (= la "1")(ssadd en settk))
            (if (= la "3")
              (progn
                (ssadd en settn)
                (if (< (min x1 x2) xmin) (setq xmin (min x1 x2)))
                (if (> (max x1 x2) xmax) (setq xmax (max x1 x2)))
              )
            )
          )
        )
      )
    )
    (setq c (1+ c))
  )
  (setq ss (ssadd))
  (setq cpddmr 0.24)
  (setq cpsdmr 0.51)
  (setq i 0 dtl 0.0)
  (while (< i (sslength settk))
    (setq en (ssname settk i))
    (setq elst (entget en))
    (setq pt1 (cdr (assoc 10 elst)))
    (setq pt2 (cdr (assoc 11 elst)))
    (setq x1 (car pt1) x2 (car pt2))
    (if (< x2 x1)
      (progn
      (setq p pt2)
      (setq pt2 pt1)
      (setq pt1 pt)
      )
    )
    (setq x1 (car pt1) y1 (cadr pt1))
    (setq x2 (car pt2) y2 (cadr pt2))
    (setq al (/ (- y2 y1) (- x2 x1)))
    (setq xd1 x1 yd1 (- y1 Hao) xd2 x2 yd2 (- y2 Hao) kdk 1)
    (if (and (< x1 xmin) (> x2 xmax))
      (progn
        (setq ud1 xmin vd1 (+ yd1 (* al (- xmin x1))))
        (setq ud2 xmax vd2 (+ yd1 (* al (- xmax x1))))
        (setq cpddmr (* (* 0.2 (- ud1 xd1)) he_so2))
        (setq cpddmr (+ cpddmr (* (* 0.2 (- xd2 ud2)) he_so2))) 
        (setq cpsdmr (* (* 0.3 (- ud1 xd1)) he_so2))
        (setq cpsdmr (+ cpsdmr (* (* 0.3 (- xd2 ud2)) he_so2))) 

     (command "line" (list xd1 yd1) (list ud1 vd1) (list ud1 (+ vd1 3.9)) "")
     (command "line" (list xd2 yd2) (list ud2 vd2) (list ud2 (+ vd2 3.9)) "")
      )
      (progn
        (if (and (> x1 xmin) (< x1 xmax)) (setq xd1 xmax yd1 (+ yd1 (* al (- xmax x1)))))
        (if (and (> x2 xmin) (< x2 xmax)) (setq xd2 xmin yd2 (+ yd1 (* al (- xmin x1)))))
        (if (and (> x1 xmin) (< x2 xmax)) (setq kdk 0))
         (command "layer" "s" "1" "")
        (if (> kdk 0) (command "line" (list xd1 yd1) (list xd2 yd2) ""))
        (setq cpddmr (+ cpddmr (* (/ (- xd2 xd1) he_so) 0.2)))
        (setq cpsdmr (+ cpsdmr (* (/ (- xd2 xd1) he_so) 0.3)))
        (command "layer" "s" 6 "")

        (if (and (> x1 xmin) (< x1 xmax)) 
          (progn
          (command "line" (list xd1 yd1) "@0,3.9" "")
          (command "line" (list xd2 yd2) "@0,3.9" "")
          (command "line" (list xd2 (+  yd2 3.45)) "@16.7606,0.1676" "")
          (command "line" (list xd2 (+ 2.5 yd2)) (list (- xd2 30) (+ 2.5 (- yd2 (* 30 al)))) "")

          ))
        (if (and (> x2 xmin) (< x2 xmax) ) 
          (progn
          (command "line" (list xd2 yd2) "@0,3.9" "" )
          (command "line" (list xd1 yd1) "@0,3.9" "")
          (command "line" (list xd1 (+  yd1 3.45)) "@-16.7606,0.1676" "")
          (command "line" (list xd1 (+ 2.5 yd1)) (list (+ xd1 30) ( + (+ yd1 2.5) (* 30 al))) "")
          ))

      )
    )
    (setq j 0)
    (while (< j (sslength settn))
      (setq en (ssname settn j))
      (setq elst (entget en))
      (setq qt1 (cdr (assoc 10 elst)))
      (setq qt2 (cdr (assoc 11 elst)))
      (setq u1 (car qt1) u2 (car qt2))
      (if (< u2 u1)
        (progn
          (setq p qt2)
          (setq qt2 qt1)
          (setq qt1 p)
        )
      )
      (setq u1 (car qt1) v1 (cadr qt1))
      (setq u2 (car qt2) v2 (cadr qt2))
      (setq be (/ (- v2 v1) (- u2 u1)))
      (setq p1 pt1 p2 pt2 q1 qt1 q2 qt2 kdk 1)
      (setq xc1 x1 yc1 y1 xc2 x2 yc2 y2)
      (setq uc1 u1 vc1 v1 uc2 u2 vc2 v2)
      (if (> x1 u1)
        (progn
          (setq uc1 x1 vc1 (+ v1 (* (- x1 u1) be)))
          (if (< x2 u2)
            (setq uc2 x2 vc2 (+ v1 (* (- x2 u1) be)))
            (setq xc2 u2 yc2 (+ y1 (* (- u2 x1) al)))
          )
          (if (> x1 u2) (setq kdk 0))
        )
        (progn
          (setq xc1 u1 yc1 (+ y1 (* (- u1 x1) al)))
          (if (> x2 u2)
            (setq xc2 u2 yc2 (+ y1 (* (- u2 x1) al)))
            (setq uc2 x2 vc2 (+ v1 (* (- x2 u1) be)))
          )
          (if (< x2 u1) (setq kdk 0))
        )
      )
      (if (> kdk 0)
        (progn
          (command "pline" (list xc1 yc1) (list xc2 yc2) (list uc2 vc2) (list uc1 vc1) "c" )
          (setq hinh (entlast))
          (ssadd hinh ss)
          (command "area" "e" hinh)
          (setq dtcon (getvar "AREA"))
          (setq dtl (+ dtl (- dtcon (* Hmat (- uc2 uc1)))))
        )
      )
      (setq j (1+ j))
    )
    (setq i (1+ i))
  )
  (command "erase" ss "")
  (setq dtl (/ dtl he_so2) )
  (if (= lop 1) (setq en (car (entsel "Thay cho so bv BTN: "))))
  (if (= lop 2) (setq en (car (entsel "Thay cho so bv CPDD: "))))
  (if (= lop 3) (setq en (car (entsel "Thay cho so bv CPSD: "))))
  (setq elst (entget en))
  (setq elst (subst (cons 1  (rtos dtl 2 2)) (assoc 1 elst) elst))
  (entmod elst)
  (command "change" en "" "p" "layer"  6 "" "")  
  (setq en (car (entsel "Thay cho so CPDD MR: ")))
  (setq elst (entget en))
  (setq elst (subst (cons 1 (rtos cpddmr 2 2)) (assoc 1 elst) elst))
  (entmod elst)
  (command "change" en "" "p" "layer"  6 "" "")  
  (setq en (car (entsel "Thay cho so CPSD MR: ")))
  (setq elst (entget en))
  (setq elst (subst (cons 1  (rtos cpsdmr 2 2)) (assoc 1 elst) elst))
  (entmod elst)
  (command "change" en "" "p" "layer"  6 "" "")  
  (setvar "OSMODE" oslast)
  (setvar "CLAYER" lalast)
)
 (prompt "\n MM: tinh dien tich theo ty le ban ve")
(defun c:MM()

  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en (car (entsel "Thay cho so : ")))
  (setq elst (entget en))
  (setq elst (subst (cons 1 (rtos dtl 2 2)) (assoc 1 elst) elst))
  (entmod elst)
  (command "change" en "" "p" "layer"  7 "" "")  
;  (print)
;  (prompt (strcat "\nTotal area : " (rtos dtl 2 2)))
;  (print)
;  (setq pt2 (getpoint "\nPoint to write: "))
;  (command "text" pt2  "0" "2" (rtos dtl 4 2))
);defun

(prompt "\n Da: tinh chieu dai")
(defun C:DA ()

  (if (= Ty_le nil)
    (progn
    (initget (+ 1 2 4))
    (print)
    (print)
    (setq Ty_le (getreal "\nTy le : "))
    )
  )
  (setq he_so (/ 1000.0 Ty_le))
  (print)
  (setq lalast (getvar "CLAYER"))
  (setq oslast (getvar "OSMODE"))
  (setvar "osmode" 33) 

  (setq s 0.0)
  (setq pt1 (getpoint "Bat dau ben trai : "))
  (if (/= pt1 nil) (progn
  (setq pt2 (getpoint "To : "))
  (while (/= pt2 nil)
    (setq x1 (car pt1) )
    (setq x2 (car pt2) )
    (setq l (- x2 x1) )  
    (setq s (+ s l))
    (setq pt1 pt2)
    (setq pt2 (getpoint "To : "))
  )
  ))
  (if (/= s 0) (setq s (+ (/ s he_so) 0)))
  
  (setq s2 0.0)
  (setq pt1 (getpoint "Bat dau ben phai : "))
  (if (/= pt1 nil) (progn
  (setq pt2 (getpoint "To : "))
  (while (/= pt2 nil)

    (setq x1 (car pt1) )
    (setq x2 (car pt2) )
    (setq l (- x2 x1) )  
    (setq s (+ s l))
    (setq pt1 pt2)
    (setq pt2 (getpoint "To : "))
  )
  ))                
 (if (/= s2 0) (setq s2 (+ (/ s2 he_so) 0)))
  (setq s (+ s s2))

  (setq en (car (entsel "Thay cho so : ")))
  (setq elst (entget en))
  (setq elst (subst (cons 1  (rtos s 2 2)) (assoc 1 elst) elst))
  (entmod elst)

  (command "change" en "" "p" "layer"  7 "" "")  
;  (print)
;  (prompt (strcat "\nChieu dai : " (rtos s 2 2)))
;  (print)
   (command "setvar" "OSMODE" oslast)

)

(prompt "\n va: tinh chieu dai vai cong them 1 ben 1m")
(defun C:VA ()

  (if (= Ty_le nil)
    (progn
    (initget (+ 1 2 4))
    (print)
    (print)
    (setq Ty_le (getreal "\nTy le : "))
    )
  )
  (setq he_so (/ 1000.0 Ty_le))
  (print)
  (setq lalast (getvar "CLAYER"))
  (setq oslast (getvar "OSMODE"))
  (setvar "osmode" 33) 

  (setq s 0.0)
  (setq pt1 (getpoint "Bat dau ben trai : "))
  (if (/= pt1 nil) (progn
  (setq pt2 (getpoint "To : "))
  (while (/= pt2 nil)
    (setq s (+ s (distance pt1 pt2)))
    (setq pt1 pt2)
    (setq pt2 (getpoint "To : "))
  )
  ))
  (if (/= s 0) (setq s (+ (/ s he_so) 2.0)))
  
  (setq s2 0.0)
  (setq pt1 (getpoint "Bat dau ben phai : "))
  (if (/= pt1 nil) (progn
  (setq pt2 (getpoint "To : "))
  (while (/= pt2 nil)
    (setq s2 (+ s2 (distance pt1 pt2)))
    (setq pt1 pt2)
    (setq pt2 (getpoint "To : "))
  )
  ))                
 (if (/= s2 0) (setq s2 (+ (/ s2 he_so) 2.0)))
  (setq s (+ s s2))

  (setq en (car (entsel "Thay cho so VDKT: ")))
  (setq elst (entget en))
  (setq elst (subst (cons 1  (rtos s 2 2)) (assoc 1 elst) elst))
  (entmod elst)

  (command "change" en "" "p" "layer"  7 "" "")  
;  (print)
;  (prompt (strcat "\nChieu dai : " (rtos s 2 2)))
;  (print)
   (command "setvar" "OSMODE" oslast)

)

(prompt "\n GG: ghi cao do")
(defun C:GG ()

  (if (= Ty_le nil)
    (progn
    (initget (+ 1 2 4))
    (print)
    (print)
    (setq Ty_le (getreal "\nTy le : "))
    )
  )
  (setq he_so (/ 1000.0 Ty_le))
  (setq Dzlast (getvar "DIMZIN"))
  (setq eclast (getvar "CMDECHO"))
  (setq lalast (getvar "CLAYER"))
  (setq oslast (getvar "OSMODE"))
  (setvar "CMDECHO" 0)
  (setvar "DIMZIN" 0)
  (setvar "OSMODE" 1)
  (command "STYLE" "2" "VN_VNI" (* 1.8 scale)  "0.85" "0" "N" "N" "N" )   
  (command "layer" "s"  7 "")
  ;;  (if (= yc nil) (progn
  (setq ptc (getpoint "\nDiem chuan : ") ) 
  (setq yc (cadr ptc))
   (setq en1 (car (entsel "Chon so cao do: ")))
   (setq elst1 (entget en1))
   (setq chso1 (cdr (assoc 1 elst1)))
   (setq hc (atof (substr chso1 1)))
  
  ;                 )
 ;;   )
   (setvar "OSMODE" 35)
   (setq ptb (getpoint "\nDiem ghi : "))
   (while (/= ptb nil)
    (setq xb (car ptb) yb (cadr ptb))
    (setq Hb (+ Hc (/ (- yb yc) he_so)))
    (setvar "OSMODE" 0)
    (setq pt (getpoint "\nNoi ghi cao do : "))
    (setq xt (car pt) yt (cadr pt))
    (if (> xt xb) (setq dx  (* 1 scale)) (setq  dx (* scale -2)) )
    (if (> xt xb)  (command "line" (list (+ xt (* 10 scale)) yt) pt (list xt yb) "")
    (command "line" (list (- xt (* 10 scale)) yt) pt (list xt yb) "")
    )
    (command "line" ptb (list (+ xt dx) yb) "")
    (setq xtt (- xt  (* scale 0.5)) xtp (+ xt   (* scale 0.5)) )
    (if (> yt yb) (setq ytg (+ yb (* 1.5 scale) )))
    (if (< yt yb) (setq ytg (- yb (* 1.5 scale) ))) 
    (command "line" (list xt yb) (list xtt ytg) (list xt ytg) "")
    (command "solid" (list xt yb) (list xtp ytg) (list xt ytg) "" "")
    (setq height (* 1.8 scale))
    (setq st1 (rtos Hb 2 2))   
    (if (> Hb 0) (setq st1 (strcat "+" st1)))
     (if (> xt xb) (command "text" (list (+ xt (* 0.5 scale)) (+ yt (* scale 0.5)) )   0  st1 )
     (command "text" (list (- xt (* scale 10)) (+ yt (* scale 0.5)))   0  st1 )
     )
    (setvar "OSMODE" 33)
    (setq ptb (getpoint "\ndiem ghi : "))
  )
  (setvar "OSMODE" oslast)
  (setvar "DIMZIN" Dzlast)
  (setvar "CLAYER" lalast)
  (setvar "CMDECHO" eclast)
)

(prompt "\n HH: doi cao do chuan de ghi cao do")
(defun C:hh ()
  
  (setq oslast (getvar "OSMODE"))
  (setq lalast (getvar "clayer"))
  (setvar "OSMODE" 1)
  (setq ptc (getpoint "\nDiem chuan <end of> : "))
  (setq yc (cadr ptc))

   (setq en1 (car (entsel "Chon so cao do: ")))
   (setq elst1 (entget en1))
   (setq chso1 (cdr (assoc 1 elst1)))
   (setq hc (atof (substr chso1 1)))
    
(print)
  (setvar "osmode" oslast)
 )

(prompt "\n ss: cong so thu nhat vao so thu hai")
(defun C:ss ()

  (setq dzlast (getvar "DIMZIN"))
  (setvar "DIMZIN" 0)
  (setq en1 (car (entsel "\n SO THU NHAT: ")))
  (while (/= en1 nil)
    (setq en2 (car (entsel "\n SO THU HAI : ")))
    (command "change" en1 en2 "" "p" "layer" 7 "" "")
    (setq elst1 (entget en1))
    (setq chso1 (cdr (assoc 1 elst1)))
    (setq so1 (atof (substr chso1 1)))
    (setq elst2 (entget en2))
    (setq chso2 (cdr (assoc 1 elst2)))
    (setq so2 (atof (substr chso2 1)))
    (setq so2 (+ so2 so1))
    ;;(setq so1 (* so1 2))
    ;;(setq elst1 (subst (cons 1 (strcat ": " (rtos so1 2 2))) (assoc 1 elst1) elst1))
    ;;(entmod elst1)
    (setq elst2 (subst (cons 1 (rtos so2 2 2)) (assoc 1 elst2) elst2))
    (entmod elst2)
    (setq en1 (car (entsel "\n SO THU NHAT: ")))
  )
  (setvar "DIMZIN" dzlast)
)


(prompt "\n ttt: tru so thu nhat vao so thu hai")
(defun C:ttt ()

  (setq dzlast (getvar "DIMZIN"))
  (setvar "DIMZIN" 0)
  (setq en1 (car (entsel "\n SO THU NHAT: ")))
  (while (/= en1 nil)
    (setq en2 (car (entsel "\n SO THU HAI : ")))
    (command "change" en1 en2 "" "p" "layer" 7 "" "")
    (setq elst1 (entget en1))
    (setq chso1 (cdr (assoc 1 elst1)))
    (setq so1 (atof (substr chso1 1)))
    (setq elst2 (entget en2))
    (setq chso2 (cdr (assoc 1 elst2)))
    (setq so2 (atof (substr chso2 1)))
    (setq so2 (- so2 so1))
    ;;(setq so1 (* so1 2))
    ;;(setq elst1 (subst (cons 1 (strcat ": " (rtos so1 2 2))) (assoc 1 elst1) elst1))
    ;;(entmod elst1)
    (setq elst2 (subst (cons 1 (rtos so2 2 2)) (assoc 1 elst2) elst2))
    (entmod elst2)
    (setq en1 (car (entsel "\n SO THU NHAT: ")))
  )
  (setvar "DIMZIN" dzlast)
)


(defun c:MMm()
  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (command "layer" "f" "5" "")
 ;;(command "layer" "f" "6" "")


  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)

    (setq pt1 (getpoint "\nPick internal point : "))
  )
  (command "setvar" "OSMODE" oslast)
  (command "erase" ss "")
  (setq ss nil)
  (command "redraw")
  (setq dtl (/ dtl tl2))
  (setq dtl (+ dtl 0.8))
  (setq en (car (entsel "Thay cho so : ")))
  (setq elst (entget en))
  (setq elst (subst (cons 1 (rtos dtl 2 2)) (assoc 1 elst) elst))
  (entmod elst)
  (command "change" en "" "p" "layer"  7 "" "")  
 (command "layer" "t" "5" "")
 ;; (command "layer" "t" "6" "")

);defun

(prompt "\n ad: cong dien tich vao mot so")
(defun c:ad()

  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en1 (car (entsel "Thay so CAN CONG THEM: ")))
 
  (setq elst1 (entget en1))
  (setq chso1 (cdr (assoc 1 elst1)))
  (setq so1 (atof (substr chso1 1)))
  (setq so1 (+ dtl so1))
  (setq elst1 (subst (cons 1 (rtos so1 2 2)) (assoc 1 elst1) elst1))
  (entmod elst1)
  (command "change" en1 "" "p" "layer"  7 "" "")  
  
   (setq en2 (car (entsel "\n Thay so DT DAO : ")))
       
    (setq elst2 (entget en2))
    (setq chso2 (cdr (assoc 1 elst2)))
    (setq so2 (atof (substr chso2 1)))
    (setq so2 so1 )
    (setq elst2 (subst (cons 1 (rtos so2 2 2)) (assoc 1 elst2) elst2))
    (entmod elst2)
    (command "change" en2 "" "p" "layer"  7 "" "")  
   
;  (print)
;  (prompt (strcat "\nTotal area : " (rtos dtl 2 2)))
;  (print)
;  (setq pt2 (getpoint "\nPoint to write: "))
;  (command "text" pt2  "0" "2" (rtos dtl 4 2))
);defun

(prompt "\n sub: tru dien tich cho mot so")
(defun c:SUB()

  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en1 (car (entsel "Thay so cong: ")))
  (setq elst1 (entget en1))
  (setq chso1 (cdr (assoc 1 elst1)))
  (setq so1 (atof (substr chso1 1)))
  (setq so1 (- so1 dtl))
  (setq elst1 (subst (cons 1 (rtos so1 2 2)) (assoc 1 elst1) elst1))
  (entmod elst1)

  (setq en2 (car (entsel "\n Thay so kq : ")))
    ;;(command "change" en1 en2 "" "p" "layer" 6 "" "")
    (setq elst2 (entget en2))
    (setq chso2 (cdr (assoc 1 elst2)))
    (setq so2 (atof (substr chso2 1)))
    (setq so2 so1)
    (setq elst2 (subst (cons 1 (rtos so2 2 2)) (assoc 1 elst2) elst2))
    (entmod elst2)

   (command "change" en2 "" "p" "layer"  7 "" "")  
;  (print)
;  (prompt (strcat "\nTotal area : " (rtos dtl 2 2)))
;  (print)
;  (setq pt2 (getpoint "\nPoint to write: "))
;  (command "text" pt2  "0" "2" (rtos dtl 4 2))
);defun

(defun C:add ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.2))
  (command "layer" "s" "2" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
    (command "line" (list x1 y1) (list x2 y2) "")
    (setq pt1 pt2)
    (setvar "OSMODE" 33)
    (setq pt2 (getpoint "To : "))
  )
       ))
  (setq dthc (/ (/ dthc he_so2) 1))
  (setq en (car (entsel "Thay so dao dat : ")))
  (setq elst (entget en))
  (setq chso (cdr (assoc 1 elst)))
  (setq so1 (atof (substr chso 1)))
  (setq so1 (+ so1 dthc))
  (setq elst (subst (cons 1  (rtos so1 2 2)) (assoc 1 elst) elst))
  (entmod elst)

  (setq en2 (car (entsel "Thay so dap dat : ")))
  (setq elst2 (entget en2))
  (setq chso2 (cdr (assoc 1 elst2)))
  (setq so2 (atof (substr chso2 1)))
  (setq so2 (+ so2 dthc))
  (setq elst2 (subst (cons 1  (rtos so2 2 2)) (assoc 1 elst2) elst2))
  (entmod elst2)

  (setq dtatb 0.00)
  (setvar "CLAYER" lalast)
 ;;(command "mm" "")
)

(defun C:tc ()
  (vmon)
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sy he_so)
  (command "layer" "s" 1 "")
  (setvar "osmode" 33)
  (print)
  (print)
  (setq pt1 (getpoint "\nChan tuong : "))
    (setq x1 (car pt1) y1 (cadr pt1) )

    (setvar "osmode" 0)
   (setvar "osmode" 512)
  (print)
  (print)
    (setq els (entget (car (entsel "Gioi han " ))))
    (setq pt3 (cdr (assoc 10 els)) pt4 (cdr (assoc 11 els)))
    (setq x3 (car pt3)  y3  (cadr pt3))
    (setq x4 (car pt4)  y4  (cadr pt4))

    (setq  y2  (+ y1 2) )

      (setq pt5 (inters (list x3 y3) (list x4 y4)  (list x1 y1) (list x1  y2) nil ))
      (setq x5 (car pt5)  y5  (cadr pt5))

    (command "line" (list x1 y1 ) (list x5 (+ y5 0)) "")
    (command "text"  (list x1 (+ y5 4) )  2.0  90 "TC" "")
    (print)
    (print)

  (setvar "OSMODE" oslast)
  (setvar "CLAYER" lalast)
  (setvar "CMDECHO" eclast)

  ;;(setvar "OSMODE" 0)
)

 (prompt "\n tn: ve tam nhin tren mcn")
(defun C:tn ()

  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sx he_so)
  (setq sy he_so)
  (setvar "OSMODE" 33)
  (command "-layer" "s" 1 "")
  (setq dy (* 1.2 sy))

(setvar "osmode" 512)
  (print)
  (print)
  (setq pt (getpoint "\nChan duong dong <nearest to> : "))
  (setq y0 (cadr pt))
  (setq yg1 (- y0 1))
  (setq yg2 (- y0 10))
  (setq yg3 (- y0 12.5))
  (setq yg4 (- y0 15))

  (setq kt 0)  

  (setvar "OSMODE" 33)
  (setq pt1 (getpoint "\nDiem bat dau ben trai: "))
      
  (if (/= pt1 nil) (progn
    (setq y1 (cadr pt1) x1 (car pt1))
    
   (setq en1 (car (entsel "Chon so cao do: ")))
   (setq elst1 (entget en1))
   (setq chso1 (cdr (assoc 1 elst1)))
   (setq hc (atof (substr chso1 1)))
   (setq dty (- (* sy hc) y1))

    (print)
    (setq kt 1)  

    (setq x2 (- x1 dy) y2 (+ y1 dy ) )
    (setq pt2 (list  x2  y2) )
    (setq h2 (/ (+ y2 dty) sy))

    (setq ll (getreal "\n Chieu dai mo rong: "))
    (setq x3 (- x2  (* ll sx)) y3 (+ y2 (* ll 0.03)) )
    (setq pt3 (list  x3  y3) )
    (setq x4 (- x3 2) y4 (+ y3 2)  )
    (setq pt4 (list  x4  y4 ) )
    (setq h3 (/ (+ y3 dty) sy))
    
     
   (setq els (entget (car (entsel "Gioi han 1:"))))
    (setq pt5 (cdr (assoc 10 els)) pt6 (cdr (assoc 11 els)))
    (setq pt7 (inters pt3 pt4  pt5 pt6 nil))
    (setq y7 (cadr pt7)    x7 (car pt7) )
    (setq h7 (/ (+ y7 dty) sy))
    (setvar "OSMODE" 0)
    (if (> ll 0) (command "line" pt1 pt2 pt3 pt7 ""))
    (if (= ll 0) (command "line" pt1  pt7 ""))                
   
    (command "-layer" "s" 7 "")

    (if (> ll 0) (progn 
    (command "line" pt2 (list x2 y0) "")
    (command "line" (list x2  yg2) (list x2 yg4 ) "")
    (command "text" "r" (list x2 yg1) 1.8 90 (rtos h2 2 2))
      ))
    
    (if (> ll 0) (progn 
    (command "line" pt3 (list x3 y0) "")
    (command "line" (list x3  yg2) (list x3 yg4 ) "")
    (command "text" "r" (list x3 yg1) 1.8 90 (rtos h3 2 2))
     ))

    (command "line" pt7 (list x7 y0) "")
    (command "line" (list x7  yg2) (list x7 yg4 ) "")
    (command "text" "r" (list x7 yg1) 1.8 90 (rtos h7 2 2))   
  
    (setq dx (- x1 x2))
    (setq xt (/ dx sx))
    (setq xg (* 0.5 (+ x1 x2)) )
    (setq sxt (rtos xt 2 2))
     (if (> ll  0) (command "text" "m" (list xg yg3) 1.8 0 sxt) )
                   
     
    (setq dx (- x2 x3))
    (setq xt (/ dx sx))
    (setq xg (*  0.5 (+ x2 x3)) )
    (setq sxt (rtos xt 2 2))
    
    (if (> ll  0) (command "text" "m" (list xg yg3) 1.8 0 sxt))
                  

    (if (> ll 0) (Progn
    (setq dx (- x3 x7))
    (setq xt (/ dx sx))
    (setq xg (*  0.5 (+ x3 x7)) )
                 ))
    (if (= ll 0) (Progn
    (setq dx (- x1 x7))
    (setq xt (/ dx sx))
    (setq xg (*  0.5 (+ x1 x7)) )
                 ))
    
    (setq sxt (rtos xt 2 2))

    (command "text" "m" (list xg yg3) 1.8 0 sxt)
 

   ))

(setvar "OSMODE" 33)
(setq pt1 (getpoint "\nDiem bat dau ben phai: "))
      
  (if (/= pt1 nil) (progn
      (if (= kt 0) (progn
   (setq y1 (cadr pt1) x1 (car pt1))
      (setq en1 (car (entsel "Chon so cao do: ")))
      (setq elst1 (entget en1))
      (setq chso1 (cdr (assoc 1 elst1)))
      (setq hc (atof (substr chso1 1)))     

      (setq dty (- (* sy hc) y1))

       (print)   
       )) 


    (setq x2 (+ x1 dy) y2 (+ y1 dy ) )
    (setq pt2 (list  x2  y2) )
    (setq h2 (/ (+ y2 dty) sy))
   
    (setq ll (getreal "\n Chieu dai mo rong: "))
    (setq x3 (+ x2  (* ll sx)) y3 (+ y2 (* ll 0.03)) )
    (setq pt3 (list  x3  y3) )
    (setq pt4 (list  (+ x3 2) (+ y3 2) ) )
    (setq h3 (/ (+ y3 dty) sy))

    (setq els (entget (car (entsel "Gioi han 1:"))))
    (setq pt5 (cdr (assoc 10 els)) pt6 (cdr (assoc 11 els)))
    (setq pt7 (inters pt3 pt4  pt5 pt6 nil))
    (setq y7 (cadr pt7)    x7 (car pt7) )
    (setq h7 (/ (+ y7 dty) sy))
    (setvar "OSMODE" 0)
    (command "-layer" "s" 1 "")
    (if (> ll 0) (command "line" pt1 pt2 pt3 pt7 ""))
    (if (= ll 0)            
    (command "line" pt1  pt7 ""))       
    

    (command "-layer" "s" 7 "")
       (if (> ll 0) (progn
    (command "line" pt2 (list x2 y0) "")
    (command "line" (list x2  yg2) (list x2 yg4 ) "")
    (command "text" "r" (list x2 yg1) 1.8 90 (rtos h2 2 2))
                    ))

         (if (> ll 0) (progn
    
    (command "line" pt3 (list x3 y0) "")
    (command "line" (list x3  yg2) (list x3 yg4 ) "")
    (command "text" "r" (list x3 yg1) 1.8 90 (rtos h3 2 2))
                       ))

    (command "line" pt7 (list x7 y0) "")
    (command "line" (list x7  yg2) (list x7 yg4 ) "")
    (command "text" "r" (list x7 yg1) 1.8 90 (rtos h7 2 2))   
  
    (setq dx (- x2 x1))
    (setq xt (/ dx sx))
    (setq xg (*  0.5 (+ x1 x2)) )
    (setq sxt (rtos xt 2 2))
       
    (if (> ll 0 ) 
    (command "text" "m" (list xg yg3) 1.8 0 sxt))

    (setq dx (- x3 x2))
    (setq xt (/ dx sx))
    (setq xg (*  0.5 (+ x2 x3)) )
    (setq sxt (rtos xt 2 2))
       (if (> ll 0 )  (command "text" "m" (list xg yg3) 1.8 90 sxt)) 
       
       (if (> ll 0 ) (Progn
    (setq dx (- x7 x3))
    (setq xt (/ dx sx))
    (setq xg (*  0.5 (+ x3 x7)) )
                     
                     ) (Progn
    (setq dx (- x7 x1))
    (setq xt (/ dx sx))
    (setq xg (*  0.5 (+ x1 x7)) )
                     ))
    
       
(setq sxt (rtos xt 2 2))
      
    (command "text" "m" (list xg yg3) 1.8 0 sxt)
    
    
  ))


  (setvar "OSMODE" oslast)
  (setvar "CLAYER" lalast)
  (setvar "CMDECHO" eclast)
)

(prompt "\n sss: cong THEM SO 1.1")
(defun C:sss ()

  (setq dzlast (getvar "DIMZIN"))
  (setvar "DIMZIN" 0)
  ;;(setq AA (getreal "\nSo cong: "))
  (setq AA  1.1)
  (setq en1 (car (entsel "\n SO CONG THEM: ")))
  
  (while (/= en1 nil)
    (setq elst1 (entget en1))
    (setq chso1 (cdr (assoc 1 elst1)))
    (setq so1 (atof (substr chso1 1)))
    (setq so1 (+  so1 AA))
    
  
   (setq elst1 (subst (cons 1 (rtos so1 2 2)) (assoc 1 elst1) elst1))
   (entmod elst1)
    
    (setq en1 (car (entsel "\n SO CONG THEM: ")))
  )
  (setvar "DIMZIN" dzlast)
)

(prompt "\n : AAA cong so thu nhat vao so thu hai")
(defun C:AAA ()

  (setq dzlast (getvar "DIMZIN"))
  (setvar "DIMZIN" 0)
  (setq en1 (car (entsel "\n SO CPDD: ")))
  (while (/= en1 nil)
    (setq en2 (car (entsel "\n SO DAP CAT : ")))
    (command "change" en1 en2 "" "p" "layer" 7 "" "")
    (setq elst1 (entget en1))
    (setq chso1 (cdr (assoc 1 elst1)))
    (setq so1 (atof (substr chso1 1)))
    (setq elst2 (entget en2))
    (setq chso2 (cdr (assoc 1 elst2)))
    (setq so2 (atof (substr chso2 1)))
    (setq so2 (+ so2 0.66))
    (setq so1 (- so1 0.66))
    (setq elst1 (subst (cons 1 (rtos so1 2 2)) (assoc 1 elst1) elst1))
    (entmod elst1)

    (setq elst2 (subst (cons 1 (rtos so2 2 2)) (assoc 1 elst2) elst2))
    (entmod elst2)
    (setq en1 (car (entsel "\n SO CPDD: ")))
  )
  (setvar "DIMZIN" dzlast)
)

(defun C:dc ()
 
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.12))
  (command "layer" "s" "1" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
    ;(command "line" (list x1 y1) (list x2 y2) "")
    (setq pt1 pt2)
    (setvar "OSMODE" 33)
    (setq pt2 (getpoint "To : "))
  )
       ))
  
    (setq dthc (/ (/ dthc he_so2) 1))
    
    (setq en1 (car (entsel "Thay so bi tru: ")))
    (setq elst1 (entget en1))
    (setq chso1 (cdr (assoc 1 elst1)))
    (setq so1 (atof (substr chso1 1)))
    (setq so1 (- so1 dthc))
    (setq elst1 (subst (cons 1  (rtos so1 2 2)) (assoc 1 elst1) elst1))
    (entmod elst1)
    
    (setq en2 (car (entsel "Thay so cong vao: ")))
        (setq elst2 (entget en2))
        (setq chso2 (cdr (assoc 1 elst2)))
        (setq so2 (atof (substr chso2 1)))
        (setq so2 (+ so2 dthc))
        (setq elst2 (subst (cons 1  (rtos so2 2 2)) (assoc 1 elst2) elst2))
    (entmod elst2)
    
    
  (setvar "CLAYER" lalast)
 ;;(command "mm" "")
)
(prompt "\n chi: tao diem chia")
(defun C:CHI (/ oslast r e en p pt g s x y xt yt he x1 y1 x2 y2)
  (setq oslast (getvar "OSMODE"))
  (setvar "OSMODE" 32)
  (setq e (entsel "Doi tuong : "))
  (setq pt (getpoint "Diem chia : "))
  (setvar "OSMODE" 0)
  (command "break" e "F" pt pt)
  (setvar "OSMODE" oslast)
)

(prompt "\n : stt ghi so thu tu")

(defun C:stt ()

  (setq dzlast (getvar "DIMZIN"))
  (setvar "DIMZIN" 0)
  (setq so1 (getint "\n SO bat dau: "))
  
   (setq en2 (car (entsel "\n SO tiep theo : ")))
   
   (progn
   (while (/= en2 nil)
   
    (setq elst2 (entget en2))
    (setq chso2 (cdr (assoc 1 elst2)))
    (setq so2 (atoi chso2))
    (setq so2 (+ so1 1))
    (setq so1 (+ so1 1))
    (setq elst2 (subst (cons 1 (strcat "T" (itoa so2))) (assoc 1 elst2) elst2))
    (entmod elst2)
    (setq en2 (car (entsel "\n SO tiep theo : ")))
    )
    )
  (setvar "DIMZIN" dzlast)
)

{>>>>>>>>>>>>>>>>>>>>>>>>>>>>>>>>>>>>>>>>>>>>>>>>>>>>>>
(prompt "\n Q1: Khoi luong phan le duong")
(defun C:Q1 ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.3))
  (setq dy2 (* he_so 0.42)) 
  (command "layer" "s" "0" "")
  (setvar "OSMODE" 33)
  (setq dthc 0)
  (setq dthc1 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dtt1 (abs (* dy2 (- x2 x1))))
    (setq dthc (+ dthc dtt))
    (setq dthc1 (+ dthc1 dtt1))
    (setvar "OSMODE" 0)
    ;(command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dtp1 (abs (* dy2 (- x2 x1))))
    (setq dthc (+ dthc dtp))
    (setq dthc1 (+ dthc1 dtp1))
    (setvar "OSMODE" 0)
    ;(command "line" (list x1 y1) (list x2 y2) "")
    (setq pt1 pt2)
    (setvar "OSMODE" 33)
    (setq pt2 (getpoint "To : "))
  )
       ))
  
  (setq dthc (/ dthc he_so2) )
  (setq dthc1 (/ dthc1 he_so2))  
    
    
    (setq dem  0)
    (setq dem (getint "may mai ta luy: "))
    (if  (= dem 1) (progn
    (setq cpdd (+ dthc  0.12))
    (setq cpsd (+ dthc1 0.26))
    (setq cpmp (+ dthc  0.39))
    ))
    (if  (= dem 2) (progn
    (setq cpdd (+ dthc  0.24))
    (setq cpsd (+ dthc1 0.51))
    (setq cpmp (+ dthc  0.78))
    ))
    (if  (= dem 0) (progn
    (setq cpdd dthc)
    (setq cpsd dthc1)
    (setq cpmp dthc)
    ))
    (setq en2 (car (entsel "Cong so CPDD : ")))
    
    (setq elst2 (entget en2))
    (setq chso2 (cdr (assoc 1 elst2)))
    (setq so2 (atof (substr chso2 1)))
    (setq so2 (+ so2 cpdd))
    (setq elst2 (subst (cons 1 (rtos so2 2 2)) (assoc 1 elst2) elst2))
    (entmod elst2)
    (command "change" en2 "" "p" "layer"  7 "" "")  
   
   
    (setq en3 (car (entsel "Cong so CPSD : ")))
    (setq elst3 (entget en3))
    (setq chso3 (cdr (assoc 1 elst3)))
    (setq so3 (atof (substr chso3 1)))
    (setq so3 (+ so3 cpsd))
    (setq elst3 (subst (cons 1 (rtos so3 2 2)) (assoc 1 elst3) elst3))
    (entmod elst3)
    (command "change" en3 "" "p" "layer"  7 "" "")  

    (setq en4 (car (entsel "Cong so CPMP : ")))
    (setq elst4 (entget en4))
    (setq chso4 (cdr (assoc 1 elst4)))
    (setq so4 (atof (substr chso4 1)))
    (setq so4 (+ so4 cpmp))
    (setq elst4 (subst (cons 1 (rtos so4 2 2)) (assoc 1 elst4) elst4))
    (entmod elst4)
    (command "change" en4 "" "p" "layer"  7 "" "")  ;

  (setq dtatb 0.00)
  (setvar "CLAYER" lalast)
 )
 
 {>>>>>>>>>>>>>>>>>>>>>>>>>>>>>>>>>>>>>>>>>>>>>>>>>>>>>>
 (prompt "\n kl: Khoi luong cac lop ao duong")
 
 (defun C:kl ()
    (if (= Ty_le nil)  (setq Ty_le (getreal "\nDrawing scale : ")))
    (setq he_so (/ 1000 Ty_le))
    (setq he_so2 (* he_so he_so))
    (setq lalast (getvar "CLAYER"))
   (setq oslast (getvar "OSMODE"))
   (setq dy1 (* he_so 0.05))
   (setq dy2 (* he_so 0.07))
   (setq dy3 (* he_so 0.30))
     (command "layer" "s" "1" "")
   (setvar "OSMODE" 33)
   (setq btnm 0)
   (setq btnt 0)
   (setq btnt 0)
   (setq cpsd 0)
   (setq pt1 (getpoint "\nDiem bat dau ben trai: "))
       (if (/= pt1 nil) (progn
   (setq pt2 (getpoint "To : "))
   (while (/= pt2 nil)
     (setq x1 (car pt1))
     (setq  x2 (car pt2))
     (setq dtt1 (abs (* dy1 (- x2 x1))))
     (setq dtt2 (abs (* dy2 (- x2 x1))))
     (setq dtt3 (abs (* dy3 (- x2 x1))))
     
     (setq btnm (+ btnm dtt1))
     (setq btnt (+ btnt dtt2))
     (setq cpsd (+ cpsd dtt3))
     
     (setvar "OSMODE" 0)
     ;;(command "line" (list x1 y1) (list x2 y2) "")
     (setq pt1 pt2)
     (setvar "OSMODE" 33)
     (setq pt2 (getpoint "To : "))
   )
        ))
   (setq pt1 (getpoint "\nDiem bat dau ben phai: "))
       (if (/= pt1 nil) (progn
   (setq pt2 (getpoint "To : "))
   (while (/= pt2 nil)
   (setq x1 (car pt1))
     (setq  x2 (car pt2))
     (setq dtt1 (abs (* dy1 (- x2 x1))))
     (setq dtt2 (abs (* dy2 (- x2 x1))))
     (setq dtt3 (abs (* dy3 (- x2 x1))))
     (setq dtt4 (abs (* dy3 (- x2 x1))))
     
     (setq btnm (+ btnm dtt1))
     (setq btnt (+ btnt dtt2))
     (setq cpsd (+ cpsd dtt3))
     (setq cpmp (+ cpsd dtt4))
 
     (setvar "OSMODE" 0)
     ;;(command "line" (list x1 y1) (list x2 y2) "")
     (setq pt1 pt2)
     (setvar "OSMODE" 33)
     (setq pt2 (getpoint "To : "))
   )
   ))
   (setq btnm (/ (/ btnm he_so2) 1))
   (setq btnt (/ (/ btnt he_so2) 1))
   (setq cpsd (/ (/ cpsd he_so2) 1))
   (setq cpmp (/ (/ cpsd he_so2) 1))
   
   (setq en (car (entsel "Thay so BTNM: ")))
   (setq elst (entget en))
   (setq elst (subst (cons 1  (rtos btnm 2 2)) (assoc 1 elst) elst))
   (entmod elst)
   
   (setq en1 (car (entsel "Thay so BTNT: ")))
     (setq elst (entget en1))
     (setq elst (subst (cons 1  (rtos btnt 2 2)) (assoc 1 elst) elst))
   (entmod elst)
   
   (setq en2 (car (entsel "Thay so CPDD: ")))
     (setq elst (entget en2))
     (setq elst (subst (cons 1  (rtos cpsd 2 2)) (assoc 1 elst) elst))
   (entmod elst)
   
   (setq en3 (car (entsel "Thay so CPSD: ")))
       (setq elst (entget en3))
       (setq elst (subst (cons 1  (rtos cpsd 2 2)) (assoc 1 elst) elst))
    (entmod elst)
 (setq en4 (car (entsel "Thay so CPMP: ")))
       (setq elst (entget en4))
       (setq elst (subst (cons 1  (rtos cpsd 2 2)) (assoc 1 elst) elst))
    (entmod elst)
   
   (setq dtatb 0.00)
   (setvar "CLAYER" lalast)
  
 )
(prompt "\n VB3: ve duong vet bun chieu sau co dinh")
(defun C:VB3 ()
 
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sx he_so)
  (setq sy he_so)
  (setvar "OSMODE" 33)
  (command "-layer" "s" 1 "")
  (setq dy (* 1.0 sy))
  (setq pt1 (getpoint "\nDiem ben trai: "))
  (setq en1 (car (entsel "Chon so cao do: ")))
  (setq elst1 (entget en1))
  (setq chso1 (cdr (assoc 1 elst1)))
  (setq hc (atof (substr chso1 1)))

      (if (/= pt1 nil) (progn
   (setq pt2 (getpoint "diem ben phai: "))
    (if (/= pt2 nil) (progn
  
    (setq y1  (cadr pt1) x1 (car pt1))
    (setq x2 (car pt2) y2 (cadr pt2))
    (setq Hd (getreal "\n cao ño vet: "))
    (setq y1 (- y1 (* (- hc Hd) sy)))
    (setq y2 y1)
    (setq pt1 (list x1 y1))
    (setq pt2 (list x2 y2))
    (setq pt3 (list (- x1 2) (+ y1 2) ))
    (setq pt4 (list (+ x2 2)  (+ y2 2)))
   
    (setq els (entget (car (entsel "Gioi han trai:"))))
    (setq pt5 (cdr (assoc 10 els)) pt6 (cdr (assoc 11 els)))
    (setq pt7 (inters pt1 pt3  pt5 pt6 nil))

   (setq els2 (entget (car (entsel "Gioi han phai:"))))
    (setq pt8 (cdr (assoc 10 els2)) pt9 (cdr (assoc 11 els2)))
    (setq pt10 (inters pt2 pt4 pt8 pt9 nil))
    (setvar "OSMODE" 0)
    (command "line" pt7 pt1 pt2 pt10 "")
    (setq pt1 pt2)
       ))
  ))

  (setvar "OSMODE" oslast)
  (setvar "CLAYER" lalast)
  (setvar "CMDECHO" eclast)
)

(prompt "\n VB4: ve duong vet bun chieu sau co dinh")
(defun C:VB4 ()
 
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sx he_so)
  (setq sy he_so)
  (setvar "OSMODE" 33)
  (command "-layer" "s" 1 "")
  (setq pt1 (getpoint "\nDiem chan taluy ben trai: "))
  (setq en1 (car (entsel "Chon so cao do: ")))
  (setq elst1 (entget en1))
  (setq chso1 (cdr (assoc 1 elst1)))
  (setq hc (atof (substr chso1 1)))

      (if (/= pt1 nil) (progn
   (setq pt2 (getpoint "diem chan taluy ben phai: "))
    (if (/= pt2 nil) (progn
  
    (setq y1  (cadr pt1) x1 (car pt1))
    (setq x2 (car pt2) y2 (cadr pt2))
    (setq Hd (getreal "\n cao do vet: "))

    (setq y3 (- y1 (* (- hc Hd) sy)))
    (setq y4 y3)
    (setq x3 (+ x1 (* (- hc Hd) sy)))
   (setq x4 (- x2 (- y2 y4)))
   (setq x5 (/ (+ x3 x4) 2))
    (setq pt1 (list x1 y1))
    (setq pt2 (list x2 y2))
    (setq pt3 (list x3 y3))
    (setq pt4 (list x4 y4))
    (setvar "OSMODE" 0)
    (command "line" pt1 pt3 pt4 pt2 "")
    (setq sxt (rtos Hd 2 2))
  (command "-layer" "s"  7 "")  
  (command "text" "m" (list (+ x5 4) (+ y4 4) ) 1.8 0 sxt)
  (command "line" (list (- x5 1.5) (+ y4 1))  (list (+ x5 1.5) (+ y4 1))  (list  x5   y4 ) (list  x5  (+ y4 2.5)) (list  (+ x5  8)  (+ y4 2.5)) "")
 

       ))
  ))

  (setvar "OSMODE" oslast)
  (setvar "CLAYER" lalast)
  (setvar "CMDECHO" eclast)
)

;------------------------------------------------------------------
(prompt "\n ppp: ve duong bao va tinh khoi luong")
(defun C:ppp ()

  (if (= Ty_le nil)
    (progn
    (initget (+ 1 2 4))
    (print)
    (print)
    (setq Ty_le (getreal "\nTy le : "))
   )
  )
  (setq he_so (/ 1000 Ty_le))
  (setq he_so2 (* he_so he_so))
  (print)
  (setq eclast (getvar "CMDECHO"))
  (setq lalast (getvar "CLAYER"))
  (setq oslast (getvar "OSMODE"))
  (setvar "CMDECHO" 0)
  (setvar "OSMODE" 0)
  
  (setq i "1 : " c 1.0)
  (setq s 0)
   (print)
   
    (repeat 2
   
    (setvar "osmode" 512)
    (setq pt1 (getpoint "\nDiem chan ta luy <nearest to> : "))
    (setq ytb (cadr pt1))
    
    (setvar "OSMODE"  1)
    (print)
    (setq pt3 (getpoint "diem mep duong: "))
    (setq x3 (car pt3)  y3  (cadr pt3))
    (setq h (/ (-  y3  ytb) he_so) )
    (print h)
       
         (setq en1 (car (entsel "Chon so cao do: ")))
         (setq elst1 (entget en1))
         (setq chso1 (cdr (assoc 1 elst1)))
         (setq hc (atof (substr chso1 1)))     
      
     (setq dy (- (* he_so hc) y3))
     (print)
         
   
     (if (< h 3) (progn
     
     (setq h2 (* 1.2  he_so) )
     (setq h1 (- h 1.2))
     (setq h1 (* h1 he_so))
     (setq l1  (* h1 2))
     (setq l2  (* h2 3))
     (setq xx1 (- x3 (* c l1)))
     (setq yy1 (- y3 h1))
     (setq hy1 (/ (+ yy1 dy) he_so))
     (setq xx2 (- xx1 (* c l2)))
     (setq yy2 (- yy1 h2))
     (setq hy2 (/ (+ yy2 dy) he_so))
     
     (setq xl1 (/ (+ xx1  x3) 2))
     (setq xl2 (/ (+ xx2  xx1) 2)) 
     (setvar "OSMODE"  0)
     (command "-layer" "s" 1 "")
     (command "pline"  (list x3 y3 ) (list xx1 yy1)  (list xx2 yy2) "" )
      (command "-layer" "s" 7 "")
     (command "pline"  (list (+ xx2 (* c 15.81)) yy2)  (list (+ xx1 (* c 1.918)) (- yy1 4.631)) 
     (list x3 (- y3 5.59))  "" )
     (setvar "osmode" 512)
      (print)
      (setq pt2 (getpoint "\nDiem goc toa do <nearest to> : "))
      (setq y0 (cadr pt2))
      (setq y5 (- y0 10))
      (setq y4 (- y5 5))
      (setq y6 (+ y5 9))
      (setvar "OSMODE"  0)
      (command "-layer" "s" 6 "")
      (command "line"  (list xx1 yy1 ) (list xx1 y0) "" )
      (command "line"  (list xx2 yy2 ) (list xx2 y0) "" )
      (command "-layer" "s" 7 "")
      (command "line"  (list xx2 y4 ) (list xx2 y5) "" )
      (command "line"  (list xx1 y4 ) (list xx1 y5) "" )
      
      (command "text" "r" (list xx1 y6) 1.8 90 (rtos hy1 2 2))
      (command "text" "r" (list xx2 y6) 1.8 90 (rtos hy2 2 2))
      (command "text" "m" (list xl1 (+ y4 2.5)) 1.8 0 (rtos (/ l1 he_so) 2 2))
      (command "text" "m" (list xl2 (+ y4 2.5)) 1.8 0 (rtos (/ l2 he_so) 2 2))
         
       ))

     (if (and (>= h  3) (< h 4.5))  (progn
     (print h)
     (setq h3  (*  1.2 he_so))
     (setq h2  (*  1.8 he_so))
     (setq h1  (* (-  h  3)  he_so) )
     (setq l1  (*  h1 1.75))
     (setq l2  (*  h2 2))
     (setq l3  (*  h3 3))
     (setq xx1 (- x3 (* c l1)))
     (setq yy1 (- y3 h1))
     (setq xx2 (- xx1 (* c l2)))
     (setq yy2 (- yy1 h2))
     (setq xx3 (- xx2 (* l3 c)))
     (setq yy3 (- yy2 h3))
     (setq hy1 (/ (+ yy1 dy) he_so))
     (setq hy2 (/ (+ yy2 dy) he_so))
     (setq hy3 (/ (+ yy3 dy) he_so))
     
     (setq xl3 (/ (+ xx3  xx2) 2))
     (setq xl2 (/ (+ xx2  xx1) 2)) 
     (setq xl1 (/ (+ xx1  x3) 2)) 
     (command "-layer" "s" 1 "")
     (setvar "OSMODE"  0)
     (command "pline"  pt3 (list xx1 yy1)  (list xx2 yy2) (list xx3 yy3)  "" )
      (command "-layer" "s" 7 "")
     (command "pline"  (list (+ xx3 (* c 15.81)) yy3)  (list (+ xx2 (* c 1.918)) (- yy2 4.631)) 
     (list (+ xx1 (* c 2.36)) (- yy1 4.41))  (list x3 (- y3 5.7588))  "" )

      (setvar "osmode" 512)
      (print)
      (setq pt (getpoint "\nDiem goc toa do <nearest to> : "))
      (setq y0 (cadr pt))
      (setq y5 (- y0 10))
      (setq y4 (- y5 5))
      (setq y6 (+ y5 9))
      (setvar "OSMODE"  0)
      (command "-layer" "s" 6 "")
      (command "line"  (list xx1 yy1 ) (list xx1 y0) "" )
      (command "line"  (list xx2 yy2 ) (list xx2 y0) "" )
      (command "line"  (list xx3 yy3 ) (list xx3 y0) "" )
      (command "-layer" "s" 7 "")
      (command "line"  (list xx2 y4 ) (list xx2 y5) "" )
      (command "line"  (list xx1 y4 ) (list xx1 y5) "" )
      (command "line"  (list xx3 y4 ) (list xx3 y5) "" )
      
      (command "text" "r" (list xx1 y6) 1.8 90 (rtos hy1 2 2))
      (command "text" "r" (list xx2 y6) 1.8 90 (rtos hy2 2 2))
      (command "text" "r" (list xx3 y6) 1.8 90 (rtos hy3 2 2))
      (command "text" "m" (list xl1 (+ y4 2.5)) 1.8 0 (rtos (/ l1 he_so) 2 2))
      (command "text" "m" (list xl2 (+ y4 2.5)) 1.8 0 (rtos (/ l2 he_so) 2 2))
      (command "text" "m" (list xl3 (+ y4 2.5)) 1.8 0 (rtos (/ l3 he_so) 2 2))

       ))
    
     (if (>= h  4.5)   (progn
     (print h)
     (setq h4  (*  1.2 he_so))
     (setq h3  (*  1.8 he_so))
     (setq h2  (*  1.5 he_so))
     (setq h1  (* (-  h  4.5)  he_so) )
     (setq l1  (*  h1 1.5))
     (setq l2  (*  h2 1.75))
     (setq l3  (*  h3 2))
     (setq l4  (*  h4 3))
     (setq xx1 (- x3 (* c l1)))
     (setq yy1 (- y3 h1))
     (setq xx2 (- xx1 (* c l2)))
     (setq yy2 (- yy1 h2))
     (setq xx3 (- xx2 (* l3 c)))
     (setq yy3 (- yy2 h3))
     (setq xx4 (- xx3 (* l4 c)))
     (setq yy4 (- yy3 h4))
     (setq hy1 (/ (+ yy1 dy) he_so))
     (setq hy2 (/ (+ yy2 dy) he_so))
     (setq hy3 (/ (+ yy3 dy) he_so))
     (setq hy4 (/ (+ yy4 dy) he_so))
     (setq xl4 (/ (+ xx3  xx4) 2))
     (setq xl3 (/ (+ xx3  xx2) 2))
     (setq xl2 (/ (+ xx2  xx1) 2)) 
     (setq xl1 (/ (+ xx1  x3) 2)) 
     
     (command "-layer" "s" 1 "")
     (setvar "OSMODE"  0)
     (command "pline"  pt3 (list xx1 yy1)  (list xx2 yy2) (list xx3 yy3)  (list xx4 yy4) "" )
      (command "-layer" "s" 7 "")
     (command "pline"  (list (+ xx4 (* c 15.81)) yy4)  (list (+ xx3 (* c 1.918)) (- yy3 4.631)) 
     (list (+ xx2 (* c 2.36)) (- yy2 4.41)) (list (+ xx1 (* c 2.63)) (- yy1 4.2558)) (list x3 (- y3 6.009))  "" )
      (setvar "osmode" 512)
      (print)
      (setq pt (getpoint "\nDiem goc toa do <nearest to> : "))
      (setq y0 (cadr pt))
      (setq y5 (- y0 10))
      (setq y4 (- y5 5))
      (setq y6 (+ y5 9))
      (setvar "OSMODE"  0)
      (command "-layer" "s" 6 "")
      (command "line"  (list xx1 yy1 ) (list xx1 y0) "" )
      (command "line"  (list xx2 yy2 ) (list xx2 y0) "" )
      (command "line"  (list xx3 yy3 ) (list xx3 y0) "" )
      (command "line"  (list xx4 yy4 ) (list xx4 y0) "" )
      (command "-layer" "s" 7 "")
      (command "line"  (list xx2 y4 ) (list xx2 y5) "" )
      (command "line"  (list xx1 y4 ) (list xx1 y5) "" )
      (command "line"  (list xx3 y4 ) (list xx3 y5) "" )
      (command "line"  (list xx4 y4 ) (list xx4 y5) "" )
      
      (command "text" "r" (list xx1 y6) 1.8 90 (rtos hy1 2 2))
      (command "text" "r" (list xx2 y6) 1.8 90 (rtos hy2 2 2))
      (command "text" "r" (list xx3 y6) 1.8 90 (rtos hy3 2 2))
      (command "text" "r" (list xx4 y6) 1.8 90 (rtos hy4 2 2))
      (command "text" "m" (list xl1 (+ y4 2.5)) 1.8 0 (rtos (/ l1 he_so) 2 2))
      (command "text" "m" (list xl2 (+ y4 2.5)) 1.8 0 (rtos (/ l2 he_so) 2 2))
      (command "text" "m" (list xl3 (+ y4 2.5)) 1.8 0 (rtos (/ l3 he_so) 2 2))
      (command "text" "m" (list xl4 (+ y4 2.5)) 1.8 0 (rtos (/ l4 he_so) 2 2))
       ))
     
        
     
     
      (setq i "2 : " c -1.0)
    
      )
 
       
      )

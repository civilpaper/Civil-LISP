(defun c:layoutstodwgs (/ ct doc exprt fda lays msg pre)
  (vl-load-com)
  (setq	fda   (getvar 'filedia)
	pre   (getstring "\n Enter filename prefix: ")
	exprt (getvar 'expert)
	ct    (getvar 'ctab)
	doc   (vla-get-activedocument (vlax-get-acad-object))
	lays  (vla-get-layouts doc)
	msg   ""
  )
  (setvar 'filedia 0)
  (setvar 'expert 5)
  (setvar 'tilemode 1)
  (command "_ucs" "_w")
  (foreach l (layoutlist)
    (setvar 'ctab l)
    (if	(> (sslength (ssget "_x" (list (cons 410 (getvar 'ctab))))) 1)
      (progn (vla-endundomark doc)
	     (vla-startundomark doc)
	     (vlax-for x lays
	       (and (/= (vla-get-name x) (getvar 'ctab)) (vl-catch-all-apply 'vla-delete (list x)))
	     )
	     (command "_-wblock" (strcat (getvar 'dwgprefix) pre l) "*")
	     (setq msg (strcat (getvar 'dwgprefix) pre l ".dwg created.\n" msg))
	     (vla-endundomark doc)
	     (command "_u")
      )
      (setq msg (strcat "Tab " l " has nothing on it and skipped.\n" msg))
    )
  )
  (setvar 'filedia fda)
  (setvar 'expert exprt)
  (setvar 'ctab ct)
  (princ msg)
)

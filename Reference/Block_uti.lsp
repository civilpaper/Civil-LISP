(prompt "\n\nL O A D I N G    B L O C K _ U T I . L S P")

;----------------------------------------------------------
(setq #Bacc 2)
;----------------------------------------------------------
(defun DXF (code elist)
     (cdr (assoc code elist))
)
;------------------------------------------------------------------
(defun USTR (bit msg def spflag / inp nval)
     (if (and def (/= def ""))
          (setq msg (strcat "\n" msg "<" def ">: ")
               inp (getstring spflag msg)
               inp (if (= inp "") def inp)
          )
          (progn
               (if (= " " (substr msg (strlen msg) 1))
                    (setq msg (strcat "\n" (substr msg 1 (1- (strlen msg))) ": "))
                    (setq msg (strcat "\n" msg ": "))
               )
               (if (= bit 1)
                    (while (= "" (setq inp (getstring spflag msg)))
                         (prompt "\nInvalid String.")
                    )
                    (setq inp (getstring spflag msg))
               )
          )
     )
     inp
)
;------------------------------------------------------------------
(defun b_get ( / ssl  nsset temp ed )
     (setq #sset (ssget))
     (setq ssl (sslength #sset) 
          nsset (ssadd)
     )
     (print ssl)
     (princ "entities found. ")  
     (princ "\nVerifying the selected entities -- please wait. ")
     (while (> ssl 0)
          (progn
               (setq temp (ssname #sset (setq ssl (1- ssl))))
               (setq ed (entget temp))
               (if (= (DXF 0 ed) "INSERT") (ssadd temp nsset))
          )
     )
     (setq ssl (sslength nsset)
          #sset nsset
     )
     (print ssl)
     (princ "INSERT entities found. ")
     (princ)
);defun b_ssget
;-----------------------------------------------------------------
(prompt "\n		BUP : Change INSERT entities to current scale")

(defun c:BUP( / ssl temp ed old new pt1 pt2 insert_pt oldscale ratio dist ang )
     (b_get)
     (if (= scale nil) (setq scale (getreal "\nInput current scale: ")))
     
     (setq ssl (sslength #sset))
     (while (> ssl 0)
          (progn
               (setq temp (ssname #sset (setq ssl (1- ssl)))
                    ed (entget temp)
                    insert_pt (dxf 10 ed)
                    
                    oldscale (dxf 41 ed) ; X_scale
                    ratio (/ scale (abs oldscale))
                    old (cons 41 (DXF 41 ed))
                    new (cons 41 (* ratio oldscale))
                    ed (subst new old ed)
                    oldscale (dxf 42 ed) ; Y_scale
                    ratio (/ scale (abs oldscale))
                    old (cons 42 (DXF 42 ed))
                    new (cons 42 (* ratio oldscale))
                    ed (subst new old ed)
                    oldscale (dxf 43 ed) ; Z_scale
                    ratio (/ scale (abs oldscale))
                    old (cons 43 (DXF 43 ed))
                    new (cons 43 (* ratio oldscale))
                    ed (subst new old ed)
               )
               (entmod ed)  
               (setq temp (entnext temp))
               
               (if (/= temp nil)
                    (progn
                         (setq ed (entget temp)
                              pt1 (dxf 10 ed)
                              pt2 (dxf 11 ed)
                         )
                         (setq TXTName (DXF 7 ed))
                         (if (OR (= TXTName "5") (= TXTName "V5"))
                              (setq  old (cons 40 (DXF 40 ed))
                                          new (cons 40 (* scale 2.5))
                                          ed (subst new old ed)
                                          ratio (/ scale (abs oldscale))
                               )
                              (setq  old (cons 40 (DXF 40 ed))
                                          new (cons 40 (* scale 1.6))
                                          ed (subst new old ed)
                                          ratio (/ scale (abs oldscale))
                               )
                          )
                          (setq  dist (distance insert_pt pt1)
                              ang (angle insert_pt pt1)
                              pt1 (polar insert_pt ang (* dist ratio))
                              dist (distance insert_pt pt2)
                              ang (angle insert_pt pt2)
                              pt2 (polar insert_pt ang (* dist ratio))
                              
                              old (cons 10 (DXF 10 ed))
                              new (cons 10 pt1)
                              ed (subst new old ed)
                              
                              old (cons 11 (DXF 11 ed))
                              new (cons 11 pt2)
                              ed (subst new old ed)
                         ); setq
                         (entmod ed)  
                         (entupd temp)
                    )
               )
          )
     )
     (princ)
);defun
;-----------------------------------------------------------------
(prompt "\n		UCD : Change CD BLOCK to current height")

(defun c:UCD( / ssl temp ed old new  insert_pt y )
     (prompt (strcat "\nYOUR CURRENT  'U C S' IS : " (getvar "UCSNAME") "\n"))
     (b_get)
     (if (= scale nil) (setq scale (getreal "\nInput current scale: ")))
     
     (setq DZ (getvar "DIMZIN"))
     (setvar "DIMZIN" 0)
     
     (setq ssl (sslength #sset))
     (while (> ssl 0)
          (progn
               (setq temp (ssname #sset (setq ssl (1- ssl)))
                    ed (entget temp)
                    insert_pt (dxf 10 ed)
                    bname (dxf 2 ed)
               )
               (if (OR (= bname "CD") (= bname "CD1") (= bname "CD2") (= bname "CD3"))
                    (progn
                         (setq temp (entnext temp)
                              ed (entget temp)
                              y (/ (cadr (trans insert_pt 0 1)) 100)
                         )
                         (cond
                              ((> y 0) (setq y (strcat "+" (rtos y 2 #Bacc))))
                              ((< y 0) (setq y (rtos y 2 #Bacc)))
                              ((= y 0) (setq y "%%p0.00"))
                         )
                         (setq old (cons 1 (DXF 1 ed))
                              new (cons 1 y)
                              ed (subst new old ed)
                         ); setq
                         (entmod ed)  
                         (entupd temp)
                    )
               )
          )
     )
     (princ)
     (setvar "DIMZIN" DZ)
);defun
;-----------------------------------------------------------------
(prompt "\n		CD  : To insert a CD block")
(defun c:cd ( / DZ pt y ptside ang OT)
     (if (= scale nil)  (setq scale (getreal "\nInput current scale: ")))
;     (if (= #Bacc nil) (setq #Bacc (getint "\nInput accuracy: ")))
     (setq DZ (getvar "DIMZIN"))
     (setvar "DIMZIN" 0)
     (setq OT (getvar "ORTHOMODE"))
     (setvar "ORTHOMODE" 0)
     (setq pt (getpoint "\nPick Insertion Point")
     		 ptside (getpoint "\nPick Side Point" pt)
		 ang (angle pt ptside)
     )

     (setq y (/ (cadr pt) 100.0))
     (cond
          ((> y 0) (setq y (strcat "+" (rtos y 2 #Bacc))))
          ((< y 0) (setq y (rtos y 2 #Bacc)))
          ((= y 0) (setq y "%%p0.00"))
     )
     (setq y (ustr 0 "Input elevation: " y T))
     ( if	 (AND (>= ang 0) (< ang 1.5708)) (command "INSERT" "CD" pt scale scale "0" y))
     ( if	 (AND (>= ang 1.5708) (< ang 3.1416)) (command "INSERT" "CD3" pt scale scale "0" y))
     ( if	 (AND (>= ang 3.1416) (< ang 4.7124)) (command "INSERT" "CD2" pt scale scale "0" y))
     ( if	 (AND (>= ang 4.7124) (< ang 6.2832)) (command "INSERT" "CD1" pt scale scale "0" y))
     (setvar "DIMZIN" DZ)
     (setvar "ORTHOMODE" OT)

)
;---------------------------------------------------------------------------
(prompt "\n		CD1 : To insert a CD block (SCALE 1:1000)")
(defun c:cd1 ( / DZ pt y ptside ang OT)
     (if (= scale nil)  (setq scale (getreal "\nInput current scale: ")))
;     (if (= #Bacc nil) (setq #Bacc (getint "\nInput accuracy: ")))
     (setq DZ (getvar "DIMZIN"))
     (setvar "DIMZIN" 0)
     (setq OT (getvar "ORTHOMODE"))
     (setvar "ORTHOMODE" 0)
     (setq pt (getpoint "\nPick Insertion Point")
     		 ptside (getpoint "\nPick Side Point" pt)
		 ang (angle pt ptside)
     )

     (setq y (/ (cadr pt) 1.0))
     (cond
          ((> y 0) (setq y (strcat "+" (rtos y 2 #Bacc))))
          ((< y 0) (setq y (rtos y 2 #Bacc)))
          ((= y 0) (setq y "%%p0.00"))
     )
     (setq y (ustr 0 "Input elevation: " y T))
     ( if	 (AND (>= ang 0) (< ang 1.5708)) (command "INSERT" "CD" pt scale scale "0" y))
     ( if	 (AND (>= ang 1.5708) (< ang 3.1416)) (command "INSERT" "CD3" pt scale scale "0" y))
     ( if	 (AND (>= ang 3.1416) (< ang 4.7124)) (command "INSERT" "CD2" pt scale scale "0" y))
     ( if	 (AND (>= ang 4.7124) (< ang 6.2832)) (command "INSERT" "CD1" pt scale scale "0" y))
     (setvar "DIMZIN" DZ)
     (setvar "ORTHOMODE" OT)

)
;---------------------------------------------------------------------------
(prompt "\n		UCD1: Change CD BLOCK to current height (SCALE 1:1000)")

(defun c:UCD1( / ssl temp ed old new  insert_pt y )
     (prompt (strcat "\nYOUR CURRENT  'U C S' IS : " (getvar "UCSNAME") "\n"))
     (b_get)
     (if (= scale nil) (setq scale (getreal "\nInput current scale: ")))
     
     (setq DZ (getvar "DIMZIN"))
     (setvar "DIMZIN" 0)
     
     (setq ssl (sslength #sset))
     (while (> ssl 0)
          (progn
               (setq temp (ssname #sset (setq ssl (1- ssl)))
                    ed (entget temp)
                    insert_pt (dxf 10 ed)
                    bname (dxf 2 ed)
               )
               (if (OR (= bname "CD") (= bname "CD1") (= bname "CD2") (= bname "CD3"))
                    (progn
                         (setq temp (entnext temp)
                              ed (entget temp)
                              y (/ (cadr (trans insert_pt 0 1)) 1.0)
                         )
                         (cond
                              ((> y 0) (setq y (strcat "+" (rtos y 2 #Bacc))))
                              ((< y 0) (setq y (rtos y 2 #Bacc)))
                              ((= y 0) (setq y "%%p0.00"))
                         )
                         (setq old (cons 1 (DXF 1 ed))
                              new (cons 1 y)
                              ed (subst new old ed)
                         ); setq
                         (entmod ed)  
                         (entupd temp)
                    )
               )
          )
     )
     (princ)
     (setvar "DIMZIN" DZ)
);defun

;---------------------------------------------------------------------------
(prompt "\n		CD2 : To insert a CD block (draw in MM)")
(defun c:cd2 ( / DZ pt y ptside ang OT)
     (if (= scale nil)  (setq scale (getreal "\nInput current scale: ")))
;     (if (= #Bacc nil) (setq #Bacc (getint "\nInput accuracy: ")))
     (setq DZ (getvar "DIMZIN"))
     (setvar "DIMZIN" 0)
     (setq OT (getvar "ORTHOMODE"))
     (setvar "ORTHOMODE" 0)
     (setq pt (getpoint "\nPick Insertion Point")
     		 ptside (getpoint "\nPick Side Point" pt)
		 ang (angle pt ptside)
     )

     (setq y (/ (cadr pt) 1000.0))
     (cond
          ((> y 0) (setq y (strcat "+" (rtos y 2 #Bacc))))
          ((< y 0) (setq y (rtos y 2 #Bacc)))
          ((= y 0) (setq y "%%p0.00"))
     )
     (setq y (ustr 0 "Input elevation: " y T))
     ( if	 (AND (>= ang 0) (< ang 1.5708)) (command "INSERT" "CD" pt scale scale "0" y))
     ( if	 (AND (>= ang 1.5708) (< ang 3.1416)) (command "INSERT" "CD3" pt scale scale "0" y))
     ( if	 (AND (>= ang 3.1416) (< ang 4.7124)) (command "INSERT" "CD2" pt scale scale "0" y))
     ( if	 (AND (>= ang 4.7124) (< ang 6.2832)) (command "INSERT" "CD1" pt scale scale "0" y))
     (setvar "DIMZIN" DZ)
     (setvar "ORTHOMODE" OT)

)
;---------------------------------------------------------------------------
(prompt "\n		UCD2: Change CD BLOCK to current height (draw in MM)")

(defun c:UCD2( / ssl temp ed old new  insert_pt y )
     (prompt (strcat "\nYOUR CURRENT  'U C S' IS : " (getvar "UCSNAME") "\n"))
     (b_get)
     (if (= scale nil) (setq scale (getreal "\nInput current scale: ")))
     
     (setq DZ (getvar "DIMZIN"))
     (setvar "DIMZIN" 0)
     
     (setq ssl (sslength #sset))
     (while (> ssl 0)
          (progn
               (setq temp (ssname #sset (setq ssl (1- ssl)))
                    ed (entget temp)
                    insert_pt (dxf 10 ed)
                    bname (dxf 2 ed)
               )
               (if (OR (= bname "CD") (= bname "CD1") (= bname "CD2") (= bname "CD3"))
                    (progn
                         (setq temp (entnext temp)
                              ed (entget temp)
                              y (/ (cadr (trans insert_pt 0 1)) 1000.0)
                         )
                         (cond
                              ((> y 0) (setq y (strcat "+" (rtos y 2 #Bacc))))
                              ((< y 0) (setq y (rtos y 2 #Bacc)))
                              ((= y 0) (setq y "%%p0.00"))
                         )
                         (setq old (cons 1 (DXF 1 ed))
                              new (cons 1 y)
                              ed (subst new old ed)
                         ); setq
                         (entmod ed)  
                         (entupd temp)
                    )
               )
          )
     )
     (princ)
     (setvar "DIMZIN" DZ)
);defun

;-----------------------------------------------------------------
(prompt "\n		MC  : To insert MC block")
(defun c:MC (  / pt1 pt2 ptside ang1 ang2 )
	(if (= scale nil) (c:tl))
	(if (= #MC nil) (setq #MC "A"))
	(setq pt1 (getpoint "\nPick the first point :")
		 pt2 (getpoint "\nPick the second point :" pt1)
;		 ptside (getpoint "\nPick Side point :" pt2)
	         	 #MC (ustr 0 "Name: " #MC T)
		 ang1 (/ (* (angle pt1 pt2) 180) PI)
	)
	(if (> ang1 180) (setq ang1 (- ang1 180)))
	(if (> ang1 0) 
		(setq  ang2 (- ang1 90))
		(setq  ang2 (+ ang1 90))
	)
	(command "INSERT" "MC3" pt1 scale scale ang2 #MC)
	(command "INSERT" "MC3" pt2 scale scale ang2 #MC)
	(setq #MC (chr (+ (ascii #MC) 1)))
);defun
;---------------------------------------------------------------------------
(prompt "\n		DOC : To insert a DDOC block")
(defun c:DOC ( / OS DZ pt1 pt2 pt x1 x2 y1 y2 y i ang )
     (if (= scale nil)
          (progn
               (setq scale (getreal "\nInput current scale: "))
          )
     )
     (setq DZ (getvar "DIMZIN"))
     (setvar "DIMZIN" 0)
     (setq pt1 (getpoint "\nPick 1st point"))
     (setq pt2 (getpoint "\nPick 2nd point" pt1))
     (setq x1 (car pt1)
          y1 (cadr pt1)
          x2 (car pt2)
          y2 (cadr pt2)
          x (/ (+ x1 x2) 2)
          y (/ (+ y1 y2) 2)
          y (+ y (* 1.5 scale))
          pt (list x y)
     )
     (setq OS (getvar "OSMODE"))
     (setvar "OSMODE" 0)
     (if (> x2 x1)
          (progn
               (setq i (* (/ (- y1 y2) (- x2 x1)) 100)
                    i (strcat (rtos i 2 #BACC) "%")
                    i (ustr 0 "Input i%: " i T)
                    ang (/ (* (angle pt1 pt2) 180) pi)
               )
               (command "INSERT" "ddoc" pt scale scale ang i)
          )
          (progn
               (setq i (* (/ (- y1 y2) (- x1 x2)) 100)
                    i (strcat (rtos i 2 #BACC) "%")
                    i (ustr 0 "Input i%: " i T)
                    ang (/ (* (angle pt2 pt1) 180) pi)
               )
               (command "INSERT" "ddoc1" pt scale scale ang i)
          )
     )
     (setvar "DIMZIN" DZ)
     (setvar "OSMODE" OS)
)
(princ)
;---------------------------------------------------------------------------

(prompt "\n		CB  : To change BLOCK to NEW BLOCK")

(defun c:CB( / ssl temp new old ed )
     (b_get) 
     (setq blname (getstring "Input name new block : " ))    
     (setq ssl (sslength #sset))
     (while (> ssl 0)
          (progn
               (setq temp (ssname #sset (setq ssl (1- ssl)))
                    ed (entget temp)
                    old (cons 2 (DXF 2 ed))                    
                    new (cons 2 blname)
                    ed (subst new old ed)
               )
               (entmod ed)  
          )
     )
     (princ)
);defun
;---------------------------------------------------------------------------
(prompt "\n		HW  : To insert a HWL block")
(defun c:HW ( / DZ pt y ptside ang OT)
     (if (= scale nil)  (setq scale (getreal "\nInput current scale: ")))
;     (if (= #acc nil) (setq #acc (getint "\nInput accuracy: ")))
     (setq DZ (getvar "DIMZIN"))
     (setvar "DIMZIN" 0)
     (setq OT (getvar "ORTHOMODE"))
     (setvar "ORTHOMODE" 0)
     (setq pt (getpoint "\nPick Insertion Point"))
     (setq y (/ (cadr pt) 100.0))
     (setq y (strcat "H.W.L +" (rtos y 2 #Bacc)))
     (setq y (ustr 0 "Input H.W.L: " y T))
     (command "INSERT" "HWL" pt scale scale "0" y)
     (setvar "DIMZIN" DZ)
     (setvar "ORTHOMODE" OT)

)
;---------------------------------------------------------------------------
(prompt "\n		DX : To insert a DX block")
(defun c:DX ( / CL pt)
     (if (= scale nil)  (setq scale (getreal "\nInput current scale: ")))
     (if (= #Bacc nil) (setq #Bacc (getint "\nInput accuracy: ")))
     (setq CL (getvar "clayer"))
     (setvar "CLAYER" "1") 	
     (setq pt (getpoint "\nPick Insertion Point"))     		 
     (command "INSERT" "DX" pt scale scale "0")
     (setvar "CLAYER" CL)

)
;--------------------------
(prompt "\n CT: To insert BLOCK COT THEP")

(defun c:ct()	
(if (= scale nil)  (setq scale (getreal "\nInput current scale: ")))
(setq pt1 (getpoint "\nPick the insert point :"))
        (command "LAYER" "S" "1" "")		
	(command "INSERT" "COTTHEP" pt1 scale scale 0)
	
);defun

;--------------------------
(prompt "\n CK1: To insert BLOCK Ch÷ ký cña Lª TuÊn Anh")

(defun c:ck1()	
(if (= scale nil)  (setq scale (getreal "\nInput current scale: ")))
(setq pt1 (getpoint "\nPick the insert point :"))
        (command "LAYER" "S" "0" "")		
	(command "INSERT" "CK11" pt1 scale scale 0)
	
);defun
;--------------------------
(prompt "\n CK2: To insert BLOCK Ch÷ ký cña Lª TuÊn Anh")

(defun c:ck2()	
(if (= scale nil)  (setq scale (getreal "\nInput current scale: ")))
(setq pt1 (getpoint "\nPick the insert point :"))
        (command "LAYER" "S" "0" "")		
	(command "INSERT" "CK22" pt1 scale scale 0)
	
);defun
;--------------------------
(prompt "\n CKL: To insert BLOCK Ch÷ ký cña NguyÔn Ngäc Linh")

(defun c:ckl()	
(if (= scale nil)  (setq scale (getreal "\nInput current scale: ")))
(setq pt1 (getpoint "\nPick the insert point :"))
        (command "LAYER" "S" "0" "")		
	(command "INSERT" "CKLnn" pt1 scale scale 0)
	
);defun

(prompt "\nNSS: NOI SUY CAO DO GIUA HAI DIEM")
(defun C:nss ()
  (command "LAYER" "N" "NSCD" "C" "4" "NSCD" "")
  (if (= Ty_le nil)
    	(progn
	    (initget (+ 1 2 4))
	    (print)
	    (print)
	    (setq Ty_le (getreal "\nTy le ban ve: "))
    	)
  )
  (setq he_so (/ 1000.0 Ty_le))
  (print)
  (setq lalast (getvar "CLAYER"))
  (setq oslast (getvar "OSMODE"))
  (setvar "osmode" 512) 
  (Setq cd1 (getreal "\nNhap Cao do diem 1 :"))
  (Setq cd2 (getreal "\nNhap Cao do diem 2 :"))
  (setq pt1 (getpoint "\nChon diem 1 : "))
  (setq pt2 (getpoint "\nChon diem 2 : "))
  (setq kc  (distance pt1 pt2))
  (if (/= kc 0) 
	(progn
		(setq kc (/ kc he_so))
		(setq doc (/ (- cd2 cd1) kc))
  	)
  )
  (if (/= pt2 nil) 
	(progn
		  (setq pt3 (getpoint "chon diem can noi suy Cao do : "))
		  (while (/= pt3 nil)
			  (setq s (/ (distance pt1 pt3) he_so))
			  (setq cd (+ cd1 (* s doc)))
			  (command "LAYER" "S" "NSCD" "")
			  (command "-style" "2" "" 0.8 0.7 0 "" "" "")
			  (command "text" "j" "BC" pt3 0 (rtos cd 2 2))
			  (setq pt2 pt3) 	
			  (setq pt3 (getpoint "chon diem can noi suy Cao do tiep theo: "))
		  )	
        )
  )
(command "setvar" "OSMODE" oslast)
(command "setvar" "CLAYER" lalast)

)
;;;---------------------------------------------
(prompt "\nssn: Tinh the tich san nen cua luoi o vuong")

(defun c:ssn ()
(setq en1 (car (entsel "Chon cao do thiet ke: ")))
	(setq elst1 (entget en1))
	(setq chso1 (cdr (assoc 1 elst1)))
	(setq cdtk (atof (substr chso1 1)))     
(setq en1 (car (entsel "Chon cao do tu nhien: ")))
	(setq elst1 (entget en1))
	(setq chso1 (cdr (assoc 1 elst1)))
	(setq cdtn (atof (substr chso1 1)))     
(setq en1 (car (entsel "Chon dien tich O : ")))
	(setq elst1 (entget en1))
	(setq chso1 (cdr (assoc 1 elst1)))
	(setq dt (atof (substr chso1 1)))     
(setq v (* (- cdtk cdtn) dt))
  (setq en (car (entsel "Thay cho so : ")))
  (setq elst (entget en))
  (setq elst (subst (cons 1 (rtos v 2 2)) (assoc 1 elst) elst))
  (entmod elst)
)
;;;---------------------------------------------
(prompt "n\n\SLSN: GHI SO LIEU RA FILE")
(defun C:SLSN ()

   (setq file (getstring T "Ten file (khong nhap phan mo rong) : "))
   (setq tenf (strcat file ".sn"))
   (setq f (open tenf "a"))
   (setq TENO (car (entsel "Chon Ten o vuong: ")))

(while (/= teno nil)  
   (setq elst1 (entget teno))
   (setq chso1 (cdr (assoc 1 elst1)))
   (setq text1 chso1 )
   (setq cso (car (entsel "So thu tu o: ")))
   (setq elst12 (entget cso))
   (setq chso12 (cdr (assoc 1 elst12)))
   (setq text12 chso12 )
   (setq text (strcat text1 text12))
   (print text)

   (setq tnt (car (entsel "Chon Cao thiet ke: ")))
   (setq elst2 (entget tnt))
   (setq chso2 (cdr (assoc 1 elst2)))
   (setq text2 chso2)
   (print text2)

   (setq tkt (car (entsel "Chon Cao do tu nhien: ")))
   (setq elst3 (entget tkt))
   (setq chso3 (cdr (assoc 1 elst3)))
   (setq text3 chso3)
   (print text3)

   (setq tnp (car (entsel "Chon dien tich: ")))
   (setq elst4 (entget tnp))
   (setq chso4 (cdr (assoc 1 elst4)))
   (setq text4 chso4)
   (print text4)

   (setq tkp (car (entsel "Chon the tich: ")))
   (setq elst5 (entget tkp))
   (setq chso5 (cdr (assoc 1 elst5)))
   (setq text5 chso5)
   (print text5)  
   (write-line (strcat text "    " text2 "    " text3 "    " text4 "    " text5) f)
   (setq teno (car (entsel "Chon ten o vuong: ")))
)
(close f)
);defun

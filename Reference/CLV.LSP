;; This LISP get value of text and convert it to Elevation
(defun c:CLV (/ elev elist en i ipt newpt ss txstr)
  (princ "\n  Select text") 
  (if (setq ss (ssget '((0 . "*TEXT"))))
    (progn
    (setq i -1)
    (repeat (sslength ss)
      (setq elist (entget (setq en (ssname ss (setq i (1+ i)))))
	    ipt (cdr (assoc 10 elist))
	    txstr (cdr (assoc 1 elist))
	    elev (atof txstr)
	    newpt (list (car ipt) (cadr ipt) elev )
	    )
      (entmod (subst (cons 10 newpt)(assoc 10 elist) elist))
      (entupd en)
      )
    )
    )
  (princ)
  )
(princ "\n\t\t* Type CLV to execute *")
(princ)

(prompt "\ndcd: dung de do tong chieu dai nhieu doan thang")
(defun C:dcd ()
  (if (= Ty_le nil)
    (progn
    (initget (+ 1 2 4))
    (print)
    (print)
    (setq Ty_le (getreal "\nTy le ban ve: "))
    )
  )
  (setq he_so (/ 1000.0 Ty_le))
  (print)
  (setq lalast (getvar "CLAYER"))
  (setq oslast (getvar "OSMODE"))
  (setvar "osmode" 33) 

  (setq s 0.0)
  (setq pt1 (getpoint "Tu diem : "))
  (if (/= pt1 nil) (progn
  (setq pt2 (getpoint "Toi diem : "))
  (while (/= pt2 nil)
    (setq s (+ s (distance pt1 pt2)))
    (setq pt1 pt2)
    (setq pt2 (getpoint "Toi diem : "))
  )
  ))
  (if (/= s 0) (setq s (/ s he_so)))
  
  (setq en (car (entsel "Ghi thay cho so : ")))
  (setq elst (entget en))
  (setq elst (subst (cons 1  (rtos s 2 2)) (assoc 1 elst) elst))
  (entmod elst)

;  (command "change" en "" "p" "layer"  7 "" "")  
  (print)
  (prompt (strcat "\nChieu dai : " (rtos s 2 2) " m"))
  (print)
   (command "setvar" "OSMODE" oslast)

)
;;;---------------------------------------------
(prompt "\nKC: dung de do khoang cach giua 2 diem")
(defun C:KC ()
  (if (= Ty_le nil)
    (progn
    (initget (+ 1 2 4))
    (print)
    (print)
    (setq Ty_le (getreal "\nTy le ban ve: "))
    )
  )
  (setq he_so (/ 1000.0 Ty_le))
  (print)
  (setq lalast (getvar "CLAYER"))
  (setq oslast (getvar "OSMODE"))
  (setvar "osmode" 33) 

  (setq s 0.0)
  (setq pt1 (getpoint "Tu diem : "))
  (if (/= pt1 nil) 
    (progn
  	(setq pt2 (getpoint "Toi diem : "))
	(while (/= pt2 nil)
		(setq s (distance pt1 pt2))
		(setq goc (/ (* (angle pt1 pt2) 180) pi))
		(setq x1 (car pt1))
		(setq y1 (cadr pt1))
		(setq x2 (car pt2))
		(setq y2 (cadr pt2))
		(setq x (/ (+ x1 x2) 2))
		(setq y (/ (+ y1 y2) 2))
		(setq pt (list X Y ))
		(if (/= s 0) (setq s (/ s he_so)))
		(command "osnap" "none")
		(command "text" "j" "BC" pt goc (rtos s 2 2))
		(command "osnap" "midpoint,endpoint,intersection,inser")

		(setq pt1 pt2)
		(setq pt2 (getpoint "Toi diem : "))
  	)
    )
)
(command "setvar" "OSMODE" oslast)
)

;;;---------------------------------------------
(prompt "\nCC: Dung de ve va ghi ten o Phia tren gieng thu")
(defun C:CC ()
  (command "LAYER" "N" "ten_gieng" "C" "131" "ten_gieng" "")
  (command "LAYER" "N" "kc_gieng" "C" "7" "kc_gieng" "")
  (if (= scale nil)  (setq scale (getreal "\nNhap Tyle ban ve: ")))
  (print)
  (setq lalast (getvar "CLAYER"))
  (setq oslast (getvar "OSMODE"))
  (setvar "osmode" 33) 
  (setq s 0)
  (setq pt1 (getpoint "Chon Diem tam duong tron dau tien: "))
  (setq R (getreal "\nNhap ban kinh duong tron: "))
  (command "Circle" pt1 R)
  (if (/= pt1 nil) 
    (progn
  	(setq pt2 (getpoint "Chon Diem chen Block Gieng thu : "))
	(setq tendau (getstring T "\nNhap ten tiep dau cua Gieng A,B,C...: "))
        (setq tenSau (getreal "\nNhap Chi so cua Gieng 1,2,3...: "))
	(while (/= pt2 nil)
		(setq goc (/ (* (angle pt1 pt2) 180) pi))
		(setq gocKT (/ (* (angle pt1 pt2) 180) pi))
		(setq b (* 2.5 SCALE))		
		(if (and (>= gocKT 90) (< gocKT 180)) 
			(progn
			    (setq goc (- gocKT 180))
      			    (setq b (* SCALE -2.5))
			)
		)	
		(if (and (>= gocKT 180) (< gocKT 270)) 
			(PROGN
			    (setq goc (- gocKT 180))
               		    (setq b (* SCALE 2.5))		
			)
		)
		(setq x1 (car pt1))
		(setq y1 (cadr pt1))
		(setq x2 (car pt2))
		(setq y2 (cadr pt2))
		(setq a (distance pt1 pt2))
		(setq c (sqrt (+ (* a a) (* b b))))
		(setq goc1 (/ (* (atan (/ b a) ) 180) pi))
		(setq goc0 (+ goc goc1))
		(setq x (+ x1 (* c (cos (/ (* goc0 pi) 180)))))
		(setq y (+ y1 (* c (sin (/ (* goc0 pi) 180)))))
		(setq pt (list X Y ))
		   (if (and (>= gocKT 90) (< gocKT 180)) 
			(progn
				(setq x (- x1 (* c (cos (/ (* goc0 pi) 180)))))
				(setq y (+ y1 (* c (abs (sin (/ (* goc0 pi) 180))))))
				(setq pt (list X Y ))				
			)
		    )		
		   (if (and (>= gocKT 180) (< gocKT 270)) 
			(progn
				(setq goc0 (- goc goc1))	
				(setq x (- x1 (* c (cos (/ (* goc0 pi) 180)))))
				(setq y (- y1 (* c (abs (sin (/ (* goc0 pi) 180))))))
				(setq pt (list X Y ))				
			)
		    )		

		(setq x0 (/ (+ x1 x2) 2))
		(setq y0 (/ (+ y1 y2) 2))
		(setq pt0 (list X0 Y0 ))
		(command "LAYER" "S" "0" "")
		(command "insert" "GT" pt2 scale scale goc)
		(command "osnap" "none")
		(command "-style" "3" "" (* 2.5 scale) 1 0 "" "" )
		(command "LAYER" "S" "ten_gieng" "")
		(command "text" "j" "C" pt goc (strcat tendau (rtos tensau 2 0)))
		(command "LAYER" "S" "kc_gieng" "")
		(command "-style" "2" "" 1.6 0.7 0 "" "" "")
		(command "text" "j" "BC" pt0 goc (rtos R 2 2))
		(command "osnap" "midpoint,endpoint,intersection,inser")
		(setq pt1 pt2)
		(setq R1 R)
		(setq R (getreal (strcat "\nNhap ban kinh duong tron tiep theo: <" (rtos R 2 2) ">" )))
		(if (= R nil) (setq R R1))
                (command "Circle" pt1 R)
		(setq pt2 (getpoint "Chon diem Chen Block gieng thu tiep theo: "))
		(setq tensau (+ tensau 1))
		(command "LAYER" "S" "0" "")
	)
    )
)
(command "setvar" "OSMODE" oslast)
)
;;;---------------------------------------------
(prompt "\nCCD: Dung de ve va ghi ten o Phia Duoi gieng thu")
(prompt "\nCopyRight by Nobody - TEDI SOUTH")
(defun C:CCD ()
  (command "LAYER" "N" "ten_gieng" "C" "131" "ten_gieng" "")
  (command "LAYER" "N" "kc_gieng" "C" "7" "kc_gieng" "")
  (if (= scale nil)  (setq scale (getreal "\nNhap tyle ban ve: ")))
  (print)
  (setq lalast (getvar "CLAYER"))
  (setq oslast (getvar "OSMODE"))
  (setvar "osmode" 33) 
  (setq s 0)
  (setq pt1 (getpoint "Chon Diem tam duong tron dau tien: "))
  (setq R (getreal "\nNhap ban kinh duong tron: "))
  (command "Circle" pt1 R)
  (if (/= pt1 nil) 
    (progn
  	(setq pt2 (getpoint "Chon Diem chen Block Gieng thu : "))
	(setq tendau (getstring T "\nNhap ten tiep dau cua Gieng A,B,C...: "))
        (setq tenSau (getreal "\nNhap Chi so cua Gieng 1,2,3...: "))
	(while (/= pt2 nil)
		(setq goc (/ (* (angle pt1 pt2) 180) pi))
		(setq gocKT (/ (* (angle pt1 pt2) 180) pi))
		(setq b (* scale -2.5))		
		(if (and (>= gocKT 90) (< gocKT 180)) 
			(progn
			    (setq goc (- gocKT 180))
		            (setq b (* scale -2.5))		
			)
		)	
		(if (and (>= gocKT 180) (< gocKT 270)) 
			(PROGN
			    (setq goc (- gocKT 180))
			    (setq b (* scale +2.5))		
			)
		)
		(setq x1 (car pt1))
		(setq y1 (cadr pt1))
		(setq x2 (car pt2))
		(setq y2 (cadr pt2))
		(setq a (distance pt1 pt2))
		(setq c (sqrt (+ (* a a) (* b b))))
		(setq goc1 (/ (* (atan (/ b a) ) 180) pi))
		(setq goc0 (+ goc goc1))
		(setq x (+ x1 (* c (cos (/ (* goc0 pi) 180)))))
		(setq y (+ y1 (* c (sin (/ (* goc0 pi) 180)))))
		(setq pt (list X Y ))
		   (if (and (>= gocKT 90) (< gocKT 180)) 
			(progn
				(setq goc0 (- goc goc1))	
				(setq x (- x1 (* c (cos (/ (* goc0 pi) 180)))))
				(setq y (+ y1 (* c (abs (sin (/ (* goc0 pi) 180))))))
				(setq pt (list X Y ))				
			)
		    )	
		   (if (and (>= gocKT 180) (< gocKT 270)) 
			(progn
				(setq x (- x1 (* c (cos (/ (* goc0 pi) 180)))))
				(setq y (- y1 (* c (abs (sin (/ (* goc0 pi) 180))))))
				(setq pt (list X Y ))				
			)
		    )		
		(setq x0 (/ (+ x1 x2) 2))
		(setq y0 (/ (+ y1 y2) 2))
		(setq pt0 (list X0 Y0 ))
		(command "LAYER" "S" "0" "")
		(command "insert" "GT" pt2 scale scale goc)
		(command "osnap" "none")
		(command "-style" "3" "" (* 2.5 scale) 1 0 "" "" )
		(command "LAYER" "S" "ten_gieng" "")
		(command "text" "j" "TC" pt goc (strcat tendau (rtos tensau 2 0)))
		(command "LAYER" "S" "kc_gieng" "")
		(command "-style" "2" "" 1.6 0.7 0 "" "" "")
		(command "text" "j" "BC" pt0 goc (rtos R 2 2))
		(command "osnap" "midpoint,endpoint,intersection,inser")
		(setq pt1 pt2)
		(setq R1 R)
		(setq R (getreal (strcat "\nNhap ban kinh duong tron tiep theo: <" (rtos R 2 2) ">" )))
		(if (= R nil) (setq R R1))
                (command "Circle" pt1 R)
		(setq pt2 (getpoint "Chon diem Chen Block gieng thu tiep theo: "))
		(setq tensau (+ tensau 1))
		(command "LAYER" "S" "0" "")
	)
    )
)
(command "setvar" "OSMODE" oslast)
)

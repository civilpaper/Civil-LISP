;;;;;http://xdvietnam.com/product/lisp-ve-thep-san-954.htm
;;;;http://www.mediafire.com/download/q7e88j3z5lcvbhb/vethepsan.lsp

;;;; DON VI BAN VE DANG VE LA m
;VE THEP AM
(DEFUN C:SA (/ OLDERR CMD OSM DK PT1 PT2  STR PRPT GOCX 
				PTD PTC)
(SETQ OLDERR *error*
      *error* myerror)
(command "layer" "m" "thep" "c" "2" """")
(SETQ CMD (GETVAR "CMDECHO"))
(SETQ OSM (GETVAR "OSMODE"))
(SETVAR "CMDECHO" 0)
(SETQ DK (GETVAR "USERR3"))
(IF (= DK 0)
    (PROGN
     (SETQ STR "1")
     (SETVAR "USERR3" 1)
    )	
    (SETQ STR (RTOS DK))
)
(SETQ PRPT (STRCAT "do dai moc (tuong la gia tri 0.08): <" STR ">:"))
(SETQ DK (GETREAL PRPT))
(IF (= DK NIL)
    (SETQ DK (GETVAR "USERR3"))
    (SETVAR "USERR3" DK)
)
(INITGET 7)
(SETQ PTD (GETPOINT "\nFrom point:"))
(INITGET 7)
(SETQ PTC (GETPOINT PTD "\nTo point:"))
(SETVAR "OSMODE" 0)
(SETQ GOCX (ANGLE PTD PTC))

(SETQ PT1 (POLAR  PTD  (- GOCX  (/ pi 2))   (* 1 DK)))
(SETQ PT2 (POLAR  PTC  (- GOCX  (/ pi 2))   (* 1 DK)))
(COMMAND "PLINE"   pt1 ptd ptc pt2   "")
(SETVAR "OSMODE" OSM)
(SETVAR "CMDECHO" CMD)
(PRINC)
)
;VE THEP DUOI
(DEFUN C:SD (/ OLDERR CMD OSM DK PT1 PT2 PT3 PT4 PT5 PT6 STR PRPT GOCX GOCY
				PTD PTC)
(SETQ OLDERR *error*
      *error* myerror)
(command "layer" "m" "thep" "c" "2" """")
(SETQ CMD (GETVAR "CMDECHO"))
(SETQ OSM (GETVAR "OSMODE"))
(SETVAR "CMDECHO" 0)
(SETQ DK (GETVAR "USERR3"))
(IF (= DK 0)
    (PROGN
     (SETQ STR "1")
     (SETVAR "USERR3" 1)
    )	
    (SETQ STR (RTOS DK))
)
(SETQ PRPT (STRCAT "Duong kinh moc tron (thuong la gia tri 0.05) <" STR ">:"))
(SETQ DK (GETREAL PRPT))
(IF (= DK NIL)
    (SETQ DK (GETVAR "USERR3"))
    (SETVAR "USERR3" DK)
)
(INITGET 7)
(SETQ PTD (GETPOINT "\nFrom point:"))
(INITGET 7)
(SETQ PTC (GETPOINT PTD "\nTo point:"))
(SETVAR "OSMODE" 0)
(SETQ GOCX (ANGLE PTD PTC))
(SETQ GOCY (+ GOCX (/ PI 2)))
(SETQ PT1 (POLAR PTD GOCX (/ (* 1 DK) 2)))
(SETQ PT2 (POLAR PTC (+ GOCX PI) (/ (* 1 DK) 2)))
(SETQ PT3 (POLAR PT1 GOCY (* 1 DK)))
(SETQ PT4 (POLAR PT2 GOCY (* 1 DK)))
(SETQ PT5 (POLAR PT3 GOCX (* 1 DK)))
(SETQ PT6 (POLAR PT4 (+ GOCX PI) (* 1 DK)))
(COMMAND "PLINE" PT5 PT3 "A" PT1 "L" PT2 "A" PT4 "L" PT6 "")
(SETVAR "OSMODE" OSM)
(SETVAR "CMDECHO" CMD)
(PRINC)
)

;-----------------***********ChuyÓn Cao §é Tő Acad Vµo Files .TXT**********------------
;********************
(defun doichu ()
  (setvar "cmdecho" 0)
  (setvar "cmdecho" 0)
  (setvar "osmode" 0)
 (if_file2) 
  ;(setq s (getstring "\nFilename <Khong-Ten>: "))
;(if (= s nul) (setq s "Khong-Ten"))
(setq fn (open filename2 "w"))
  (write-line (strcat  "Elevation" " " "Easting" " " "Northing") fn)
  (setq i 0)
  (setq j 1)
  (prompt "\n")
  (prompt "\Chän C¸c §iÓm Cao §é : ")
  (setq ss  (ssget (list (cons 0 "Text"))))
  (if ss
                (progn
                       (repeat (sslength ss)			 
			 (setq ent (entget (ssname ss i)))			  
			 (setq nd (cdr (assoc 1 ent)))
			 (setq ss1 (cdr (assoc 72 ent)))
			 (setq ss2 (cdr (assoc 73 ent)))
			 	(if (and (= ss1 0) (= ss2 0))
			   		(setq td (cdr (assoc 10 ent)))
			   		(setq td (cdr (assoc 11 ent)))
			 	)
			 ;(setq td1 (cdr (assoc 10 ent)))
			(setq Y (cadr td))
			(setq X (car td))
			 (setq z (caddr td))
			(write-line (strcat (rtos j 2 0) "	" (rtos X 2 4) "	" (rtos Y 2 4) "	" nd) fn)
			 (setq i (+ i 1))
			(setq j (+ j 1))
     			)
		  )
    )
  (close fn)
  (setvar "osmode" 191)
  (prompt "\n****    Chóc Bąn Thµnh C«ng	***")
  (princ)  
)
;********************************
;**********************************
(defun c:tsn ()
  (setvar "cmdecho" 0)
  (setq s (getstring "\nFilename <Khong-Ten>: "))
(if (= s nul) (setq s "Khong-Ten"))
(setq fn (open (strcat "d:/" s ".txt") "a"))
  (while
    (setq stt (getreal "STT:"))
    (dtich)
  (prompt "\n")
  (prompt "\Chän C¸c §iÓm Cao §é : ")
  (setq ss  (ssget (list (cons 0 "Text"))))
  (setq cd (sslength ss))
  (if ss
                (progn
		  (cond
		    ((= cd 5)
		     (progn
			  (setq ent1 (entget (ssname ss 0)))
			  (setq ent2 (entget (ssname ss 1)))
			  (setq ent3 (entget (ssname ss 2)))
			  (setq ent4 (entget (ssname ss 3)))
			  (setq ent5 (entget (ssname ss 4)))
			  (setq nd1 (cdr (assoc 1 ent1)))
			 (setq nd2 (cdr (assoc 1 ent2)))
			 (setq nd3 (cdr (assoc 1 ent3)))
			 (setq nd4 (cdr (assoc 1 ent4)))
			(setq nd5 (cdr (assoc 1 ent5)))			 
			(write-line (strcat nd " " nd1 " " nd2 " " nd3 " " nd4 " " nd5 " " dt) fn)
		       )
		     )

		    ((= cd 4)
		     (progn
			  (setq ent1 (entget (ssname ss 0)))
			  (setq ent2 (entget (ssname ss 1)))
			  (setq ent3 (entget (ssname ss 2)))
			  (setq ent4 (entget (ssname ss 3)))
			  ;(setq ent5 (entget (ssname ss 4)))
			  (setq nd1 (cdr (assoc 1 ent1)))
			 (setq nd2 (cdr (assoc 1 ent2)))
			 (setq nd3 (cdr (assoc 1 ent3)))
			 (setq nd4 (cdr (assoc 1 ent4)))
		         (setq nd5 (rtos 0 2 0))
			;(setq nd5 (cdr (assoc 1 ent5)))			 
			(write-line (strcat nd " " nd1 " " nd2 " " nd3 " " nd4 " " nd5  " " dt) fn)
		       )
		     )

		    ((= cd 3)
		     (progn
			  (setq ent1 (entget (ssname ss 0)))
			  (setq ent2 (entget (ssname ss 1)))
			  (setq ent3 (entget (ssname ss 2)))
			  ;(setq ent4 (entget (ssname ss 3)))
			  ;(setq ent5 (entget (ssname ss 4)))
			  (setq nd1 (cdr (assoc 1 ent1)))
			 (setq nd2 (cdr (assoc 1 ent2)))
			 (setq nd3 (cdr (assoc 1 ent3)))
			 (setq nd4 (rtos 0 2 0))
		         (setq nd5 (rtos 0 2 0))
			;(setq nd5 (cdr (assoc 1 ent5)))			 
			(write-line (strcat nd " " nd1 " " nd2 " " nd3 " " nd4 " " nd5  " " dt) fn)
		       )
		     )
		    
		     )
     			
		  )
    )
  )
  (close fn)
  (prompt "\n****    Chóc Bąn Thµnh C«ng	***")
  (princ)
)
;*********
(defun c:dc ()
      (doichu)      
  )
;;***************************Mo file
(defun if_file1 (/ name1)
               (setq name1 (getfiled "Më TËp Tin Chřa Sč LiÖu"
                            (strcat "d:/" "solieu") "txt" 2))
               (if name1 (setq filename1 (strcase name1)))                        
               )
;****************************Ghi file
(defun if_file2 (/ name2)
               (setq name2 (getfiled "L­u TËp Tin Sč LiÖu"
                            (strcat "d:/" "solieu") "txt" 1))
               (if name2 (setq filename2 (strcase name2)))                        
               )

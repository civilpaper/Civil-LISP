;==============================================================================
(defun c:st(/ unit ss cl dz ot ssa ssl i stt si sname pt ptside ang os)
  (command ".UNDO" "BE")
  (setq unit (getvar "INSUNITS"))
  (setvar "INSUNITS" 4)
  (if (= ly_scale nil) (c:tl))
  (setq ss (ssadd))
  (if (= #Bacc nil) (setq #Bacc (getint "\nS\U+1ED1 ch\U+1EEF s\U+1ED1 th\U+1EADp phân: ")))
  (setq CL (getvar "clayer"))
  (setvar "CLAYER" "0") 	
  (setq DZ (getvar "DIMZIN"))
  (setvar "DIMZIN" 0)
  (setq OT (getvar "ORTHOMODE"))
  (setvar "ORTHOMODE" 0)
  
  (setq ssa (ssget "x"))
  (setq ssl (sslength ssa))
  (setq i 0)
  (setq stt 0)
  (while (< i ssl)
    (setq si (cdr (assoc 0 (entget (ssname ssa i)))))
    (setq sname (cdr (assoc 2 (entget (ssname ssa i)))))
    (if (and (= si "INSERT") (= (substr sname 1 2) "st")) (setq stt (+ stt 1)))
    (setq i (+ i 1))
  )
  (setq stt (+ stt 1))
  (setq pt (getpoint "\nCh\U+1ECDn \U+0111i\U+1EC3m c\U+1EA7n l\U+1EA5y lý trình: ")
	ptside (getpoint "\nPh\U+01B0\U+01A1ng chèn: " pt)
	ang (angle pt ptside)
  )
  (setq os (getvar "OSMODE"))
  (setvar "OSMODE" 0)
  (if (AND (>= ang 0) (< ang 1.5708)) (command ".INSERT" "coor_RU" pt ly_scale ly_scale "0" (rtos stt 2 0)))
     ( if	 (AND (>= ang 1.5708) (< ang 3.1416)) (command ".INSERT" "coor_LU" pt ly_scale ly_scale "0" (rtos stt 2 0)))
     ( if	 (AND (>= ang 3.1416) (< ang 4.7124)) (command ".INSERT" "coor_LD" pt ly_scale ly_scale "0" (rtos stt 2 0)))
     ( if	 (AND (>= ang 4.7124) (< ang 6.2832)) (command ".INSERT" "coor_RD" pt ly_scale ly_scale "0" (rtos stt 2 0)))
  (setq ss (ssadd (entlast) ss))
  (setvar "OSMODE" os)
  (bup ss)
  (setvar "DIMZIN" DZ)
  (setvar "ORTHOMODE" OT)
  (setvar "CLAYER" CL)
  (setvar "INSUNITS" unit)
  
  (setvar "INSUNITS" unit)
  (command ".UNDO" "E")
)
;==============================================================================
(defun c:s2f(/ cent start cente cenl clobj start st lene ss ssl coor_ss i sname
	     all all_len licoor_st i_ename i_cat i_name i1_value i2_value licoor_att tf f l ssi tpt pti ptp len sta)
  (setq cent (entsel "\nCh\U+1ECDn \U+0111\U+01B0\U+1EDDng tim: "))
  (setq start (getpoint "\nG\U+1ED1c tuy\U+1EBFn: "))
  (setq cente (entget (car cent)))

  (command "area" "Object" (car cent))
  (setq cenl (getvar "perimeter"))
  (vl-load-com)
  (setq clobj (vlax-ename->vla-object (car cent)))
  (setq st (vlax-curve-getStartPoint clobj))
  (if (and (= (car start) (car st))
	   (= (cadr start) (cadr st))
	   (= (caddr start) (caddr st))
      )
    (setq lene 0)
    (setq lene cenl)
    
  )

  (setq ss (ssget "x"))
  (setq ssl (sslength ss))
  (setq coor_ss (ssadd))
  (setq i 0)
  (while (< i ssl)
    (setq si (cdr (assoc 0 (entget (ssname ss i)))))
    (setq sname (cdr (assoc 2 (entget (ssname ss i)))))
    (if (and (= si "INSERT") (or
			       (= sname "coor_RU")
			       (= sname "coor_LU")
			       (= sname "coor_RD")
			       (= sname "coor_LD")
			       )
	     )
      (progn
	(setq coor_ss (ssadd (ssname ss i) coor_ss))
      )
    )
    (setq i (+ i 1))
  )
  (setq all coor_ss)
  (setq all_len (sslength all))
  (setq i 0)
  (setq licoor_st '())
  (while (< i all_len)
      (setq i_ename (ssname all i))
      (setq i_cat (cdr (assoc 0 (entget i_ename))))
      (if (= i_cat "INSERT")
	(progn
	  (setq i_name (cdr (assoc 2 (entget i_ename))))
	  (if (or
			       (= i_name "coor_RU")
			       (= i_name "coor_LU")
			       (= i_name "coor_RD")
			       (= i_name "coor_LD")
			       )
	    (progn
	      (setq i2_value (cdr (assoc 10 (entget i_ename))))
	      (While (/= i_cat "SEQEND")
		   (if (= i_cat "ATTRIB")
		    (progn
		      
		      (if (= (setq i_tag (cdr (assoc 2 (entget i_ename)))) "PT")
			(setq i1_value (cdr (assoc 1 (entget i_ename))))
		      )
		      (if (/= i1_value nil) (setq licoor_att (list i1_value)))
     
		    )
		  )
		  (setq i_ename (entnext i_ename))
		  (setq i_cat (cdr (assoc 0 (entget i_ename))))
              )
	      (setq licoor_att (list i1_value i2_value))
	      (if (/= licoor_att nil) (setq licoor_st (cons licoor_att licoor_st)))
	    )
	  )
	)
      )
      (setq i (+ i 1))
  )

  (setq tf (getstring "\nTên t\U+1EADp tin d\U+1EEF li\U+1EC7u: "))
  (setq tf (strcat (getvar "DWGPREFIX") tf ".txt"))
  (setq f (open tf "a")) 
  (setq l (length licoor_st))
  (write-line (strcat "No."  (chr 9) "Station" (chr 9) "Distance") f)
  (setq i 0)
  (while (< i l)
    (setq ssi (nth i licoor_st))
    (setq tpt (nth 0 ssi))
    (setq pti (nth 1 ssi))
    (setq ptp (vlax-curve-getClosestPointTo clobj pti))
    (setq dis (distance pti ptp))
    (setq dis (rtos dis 2 #Bacc))
    (setq len (vlax-curve-getDistAtPoint clobj ptp))
    (if (/= lene 0)
      (setq sta (- lene len))
      (setq sta len)
    )
    (setq sta (rtos sta 2 #Bacc))
    
    (write-line (strcat tpt  (chr 9) sta (chr 9) dis) f)
    (setq i (+ 1 i))

  )
  (close f)
 
)

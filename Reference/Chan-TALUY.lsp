(defun C:TLT()
  (vmon)
  (setq eclast (getvar "CMDECHO"))
  (setq oslast (getvar "OSMODE"))
  (setvar "CMDECHO" 0)
  (setvar "OSMODE" 1)
  (command "pline")
  (setq pt0 (getpoint "\nTu diem <nearest to>  : "))
  (initget (+ 1 2 4))
  (setq l0 (getreal "\nSang trai : "))
  (setq x0 (car pt0) y0 (cadr pt0))
  (setq pt1 (getpoint "\nDen diem <nearest to> : "))
  (setq dl (distance pt0 pt1))
  (setq heso (/ l0 dl))
  (setq x1 (car pt1) y1 (cadr pt1))
  (setq u3 (- x1 x0) v3 (- y1 y0))
  (setq u1 (- x0 (* heso v3)) v1 (+ y0 (* heso u3)))
  (while (/= pt1 nil)
    (setvar "OSMODE" 0)
    (command (list u1 v1))
    (print)
    (print)
    (initget (+ 1 2 4))
    (setq l1 (getreal "\nSang trai : "))
    (setq x1 (car pt1) y1 (cadr pt1))
    (setq u3 (- x1 x0) v3 (- y1 y0))
    (setq dl (distance pt0 pt1))
    (setq heso (/ l1 dl))
    (setq u1 (- x1 (* heso v3)) v1 (+ y1 (* heso u3)))
    (setq x0 x1 y0 y1)
    (setq pt0 pt1)
    (setvar "OSMODE" 1)
    (print)
    (setq pt1 (getpoint "\nDen diem <nearest to> : "))
  )
  (setvar "OSMODE" 0)
  (command (list u1 v1) "")
  (setvar "OSMODE" oslast)
  (setvar "CMDECHO" eclast)
 )
;*
;*
;*
(defun C:TLP()
  ;(vmon)
  (setq eclast (getvar "CMDECHO"))
  (setq oslast (getvar "OSMODE"))
  (setvar "CMDECHO" 0)
  (setvar "OSMODE" 4)
  (command "osnap" "midpoint,endpoint,intersection,inser")
  (command "pline")
  (setq pt0 (getpoint "\nTu diem <nearest to>  : "))
  (initget (+ 1 2 4))
  (setq l0 (getreal "\nSang phai : "))
  (setq x0 (car pt0) y0 (cadr pt0))
  (setq pt1 (getpoint "\nDen diem <nearest to> : "))
  (setq dl (distance pt0 pt1))
  (setq heso (/ l0 dl))
  (setq x1 (car pt1) y1 (cadr pt1))
  (setq u3 (- x1 x0) v3 (- y1 y0))
  (setq u1 (+ x0 (* heso v3)) v1 (- y0 (* heso u3)))
  (while (/= pt1 nil)
    (setvar "OSMODE" 0)
    (command (list u1 v1))
    (print)
    (print)
    (initget (+ 1 2 4))
    (setq l1 (getreal "\nSang phai : "))
    (setq x1 (car pt1) y1 (cadr pt1))
    (setq u3 (- x1 x0) v3 (- y1 y0))
    (setq dl (distance pt0 pt1))
    (setq heso (/ l1 dl))
    (setq u1 (+ x1 (* heso v3)) v1 (- y1 (* heso u3)))
    (setq x0 x1 y0 y1)
    (setq pt0 pt1)
    (setvar "OSMODE" 4)
    (print)
    (setq pt1 (getpoint "\nDen diem <nearest to> : "))
  )
  (setvar "OSMODE" 0)
  (command (list u1 v1) "")
  (setvar "OSMODE" oslast)
  (setvar "CMDECHO" eclast)
)

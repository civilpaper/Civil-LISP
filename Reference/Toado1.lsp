(defun c:td()
(setq file (getstring T "Ten file toa do : "))
(setq tenf (strcat file ".tdo"))
(setq f (open tenf "a"))
(setq ST1 (getstring "Ten diem : "))
(setq pt1 (getpoint "Toa do diem : ")) 
(while (/= pt1 nil)
    (print)
    (setq x1 (car pt1) y1 (cadr pt1))
    (setq xx1 (rtos x1 2 4) yy1 (rtos y1 2 4))
    (write-line (strcat ST1 "      " xx1 "      " yy1) f)
    (setq ST1 (getstring "Ten diem : "))
    (setq pt1 (getpoint "Toa do diem : ")) 
)
(close f)
(princ)
)
(prompt "\nTD : Ghi toa do diem ra file")

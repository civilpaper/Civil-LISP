(defun DXF (code elist)
     (cdr (assoc code elist))
)
(vmon)
(setq last (getvar "OSMODE")
      LLAST (getvar "CLAYER"))
(command "setvar" "OSMODE" "33")
(command "setvar" "DIMZIN" 0 )
(prompt "\n LSP DUNG DE TINH KL TRAC NGANG ")
(prompt "\n v4  : TINH DT/2 H  BU VENH (4CM: BTN min + H: BTN tho) ")
(prompt "\n v1  : TINH DT/2 H1 BU VENH (4CM: BTN min + 6CM: BTN tho + H1: DA DAM) ")
(prompt "\n AR2 : TINH DT/2 ")
(prompt "\n HC  : TINH DT/2 30cm VET HC")
(prompt "\n 00  : DT/2 = 0.00 ")

;=================================================
(defun C:v4 ()
  (if (= Ty_le nil) (progn
    (setq Ty_le (getreal "\nDrawing scale : "))
                     )
 )
  (setq he_so (/ 1000 Ty_le))
  (setq he_so2 (* he_so he_so))
  (setq Hmat (* 0.04 he_so))
  (setq Hao (* 0.50  he_so))
  (setq lalast (getvar "CLAYER"))
  (setq oslast (getvar "OSMODE"))
  (setq settk (ssadd))
  (setq settn (ssadd))
  (setq ss (ssget))
  (setq c 0)
  (setq xmin 9000000 xmax -9000000)
  (command "layer" "s" "THKE" "")
  (setvar "OSMODE" 0)
  (while (< c (sslength ss))
    (setq en (ssname ss c))
    (setq elst (entget en))
    (setq loai (cdr (assoc 0 elst)))
    (if (= loai "LINE")
      (progn
        (setq pt1 (cdr (assoc 10 elst)) pt2 (cdr (assoc 11 elst)))
        (setq x1 (car pt1) x2 (car pt2))
        (if (> (abs (- x2 x1)) 0.001)
          (progn
            (setq la (cdr (assoc 8 elst)))
            (if (= la "THKE")(ssadd en settk))
            (if (= la "THNHIEN")
              (progn
                (ssadd en settn)
                (if (< (min x1 x2) xmin) (setq xmin (min x1 x2)))
                (if (> (max x1 x2) xmax) (setq xmax (max x1 x2)))
              )
            )
          )
        )
      )
    )
    (setq c (1+ c))
  )
  (setq ss (ssadd))
  (setq i 0 dtl 0.0)
  (while (< i (sslength settk))
    (setq en (ssname settk i))
    (setq elst (entget en))
    (setq pt1 (cdr (assoc 10 elst)))
    (setq pt2 (cdr (assoc 11 elst)))
    (setq x1 (car pt1) x2 (car pt2))
    (if (< x2 x1)
      (progn
      (setq p pt2)
      (setq pt2 pt1)
      (setq pt1 pt)
      )
    )
    (setq x1 (car pt1) y1 (cadr pt1))
    (setq x2 (car pt2) y2 (cadr pt2))
    (setq al (/ (- y2 y1) (- x2 x1)))
    (setq xd1 x1 yd1 (- y1 Hao) xd2 x2 yd2 (- y2 Hao) kdk 1)
    (if (and (< x1 xmin) (> x2 xmax))
      (progn
        (setq ud1 xmin vd1 (+ yd1 (* al (- xmin x1))))
        (setq ud2 xmax vd2 (+ yd1 (* al (- xmax x1))))
        (command "line" (list xd1 yd1) (list ud1 vd1) "")
        (command "line" (list xd2 yd2) (list ud2 vd2) "")
      )
      (progn
        (if (and (> x1 xmin) (< x1 xmax)) (setq xd1 xmax yd1 (+ yd1 (* al (- xmax x1)))))
        (if (and (> x2 xmin) (< x2 xmax)) (setq xd2 xmin yd2 (+ yd1 (* al (- xmin x1)))))
        (if (and (> x1 xmin) (< x2 xmax)) (setq kdk 0))
        (if (> kdk 0) (command "line" (list xd1 yd1) (list xd2 yd2) ""))
      )
    )
    (setq j 0)
    (while (< j (sslength settn))
      (setq en (ssname settn j))
      (setq elst (entget en))
      (setq qt1 (cdr (assoc 10 elst)))
      (setq qt2 (cdr (assoc 11 elst)))
      (setq u1 (car qt1) u2 (car qt2))
      (if (< u2 u1)
        (progn
          (setq p qt2)
          (setq qt2 qt1)
          (setq qt1 p)
        )
      )
      (setq u1 (car qt1) v1 (cadr qt1))
      (setq u2 (car qt2) v2 (cadr qt2))
      (setq be (/ (- v2 v1) (- u2 u1)))
      (setq p1 pt1 p2 pt2 q1 qt1 q2 qt2 kdk 1)
      (setq xc1 x1 yc1 y1 xc2 x2 yc2 y2)
      (setq uc1 u1 vc1 v1 uc2 u2 vc2 v2)
      (if (> x1 u1)
        (progn
          (setq uc1 x1 vc1 (+ v1 (* (- x1 u1) be)))
          (if (< x2 u2)
            (setq uc2 x2 vc2 (+ v1 (* (- x2 u1) be)))
            (setq xc2 u2 yc2 (+ y1 (* (- u2 x1) al)))
          )
          (if (> x1 u2) (setq kdk 0))
        )
        (progn
          (setq xc1 u1 yc1 (+ y1 (* (- u1 x1) al)))
          (if (> x2 u2)
            (setq xc2 u2 yc2 (+ y1 (* (- u2 x1) al)))
            (setq uc2 x2 vc2 (+ v1 (* (- x2 u1) be)))
          )
          (if (< x2 u1) (setq kdk 0))
        )
      )
      (if (> kdk 0)
        (progn
          (command "pline" (list xc1 yc1) (list xc2 yc2) (list uc2 vc2) (list uc1 vc1) "c" )
          (setq hinh (entlast))
          (ssadd hinh ss)
          (command "area" "e" hinh)
          (setq dtcon (getvar "AREA"))
          (setq dtl (+ dtl (- dtcon (* Hmat (- uc2 uc1)))))
        )
      )
      (setq j (1+ j))
    )
    (setq i (1+ i))
  )
  (command "erase" ss "")
  (setq dtl (/ (/ dtl he_so2) 2))
  (setq en (car (entsel "Thay cho so : ")))
  (setq elst (entget en))
  (setq elst (subst (cons 1 (strcat "" (rtos dtl 2 2))) (assoc 1 elst) elst))
  (entmod elst)
  (setvar "OSMODE" oslast)
  (setvar "CLAYER" lalast)
)
;=================================================
(defun C:v1 ()
  (if (= Ty_le nil) (progn
    (setq Ty_le (getreal "\nDrawing scale : "))
                     )
 )
  (setq he_so (/ 1000 Ty_le))
  (setq he_so2 (* he_so he_so))
  (setq Hmat (* 0.10 he_so))
  (setq Hao  (* 0.50  he_so))
  (setq lalast (getvar "CLAYER"))
  (setq oslast (getvar "OSMODE"))
  (setq settk (ssadd))
  (setq settn (ssadd))
  (setq ss (ssget))
  (setq c 0)
  (setq xmin 9000000 xmax -9000000)
  (command "layer" "s" "THKE" "")
  (setvar "OSMODE" 0)
  (while (< c (sslength ss))
    (setq en (ssname ss c))
    (setq elst (entget en))
    (setq loai (cdr (assoc 0 elst)))
    (if (= loai "LINE")
      (progn
        (setq pt1 (cdr (assoc 10 elst)) pt2 (cdr (assoc 11 elst)))
        (setq x1 (car pt1) x2 (car pt2))
        (if (> (abs (- x2 x1)) 0.001)
          (progn
            (setq la (cdr (assoc 8 elst)))
            (if (= la "THKE")(ssadd en settk))
            (if (= la "THNHIEN")
              (progn
                (ssadd en settn)
                (if (< (min x1 x2) xmin) (setq xmin (min x1 x2)))
                (if (> (max x1 x2) xmax) (setq xmax (max x1 x2)))
              )
            )
          )
        )
      )
    )
    (setq c (1+ c))
  )
  (setq ss (ssadd))
  (setq i 0 dtl 0.0)
  (while (< i (sslength settk))
    (setq en (ssname settk i))
    (setq elst (entget en))
    (setq pt1 (cdr (assoc 10 elst)))
    (setq pt2 (cdr (assoc 11 elst)))
    (setq x1 (car pt1) x2 (car pt2))
    (if (< x2 x1)
      (progn
      (setq p pt2)
      (setq pt2 pt1)
      (setq pt1 pt)
      )
    )
    (setq x1 (car pt1) y1 (cadr pt1))
    (setq x2 (car pt2) y2 (cadr pt2))
    (setq al (/ (- y2 y1) (- x2 x1)))
    (setq xd1 x1 yd1 (- y1 Hao) xd2 x2 yd2 (- y2 Hao) kdk 1)
    (if (and (< x1 xmin) (> x2 xmax))
      (progn
        (setq ud1 xmin vd1 (+ yd1 (* al (- xmin x1))))
        (setq ud2 xmax vd2 (+ yd1 (* al (- xmax x1))))
        (command "line" (list xd1 yd1) (list ud1 vd1) "")
        (command "line" (list xd2 yd2) (list ud2 vd2) "")
      )
      (progn
        (if (and (> x1 xmin) (< x1 xmax)) (setq xd1 xmax yd1 (+ yd1 (* al (- xmax x1)))))
        (if (and (> x2 xmin) (< x2 xmax)) (setq xd2 xmin yd2 (+ yd1 (* al (- xmin x1)))))
        (if (and (> x1 xmin) (< x2 xmax)) (setq kdk 0))
        (if (> kdk 0) (command "line" (list xd1 yd1) (list xd2 yd2) ""))
      )
    )
    (setq j 0)
    (while (< j (sslength settn))
      (setq en (ssname settn j))
      (setq elst (entget en))
      (setq qt1 (cdr (assoc 10 elst)))
      (setq qt2 (cdr (assoc 11 elst)))
      (setq u1 (car qt1) u2 (car qt2))
      (if (< u2 u1)
        (progn
          (setq p qt2)
          (setq qt2 qt1)
          (setq qt1 p)
        )
      )
      (setq u1 (car qt1) v1 (cadr qt1))
      (setq u2 (car qt2) v2 (cadr qt2))
      (setq be (/ (- v2 v1) (- u2 u1)))
      (setq p1 pt1 p2 pt2 q1 qt1 q2 qt2 kdk 1)
      (setq xc1 x1 yc1 y1 xc2 x2 yc2 y2)
      (setq uc1 u1 vc1 v1 uc2 u2 vc2 v2)
      (if (> x1 u1)
        (progn
          (setq uc1 x1 vc1 (+ v1 (* (- x1 u1) be)))
          (if (< x2 u2)
            (setq uc2 x2 vc2 (+ v1 (* (- x2 u1) be)))
            (setq xc2 u2 yc2 (+ y1 (* (- u2 x1) al)))
          )
          (if (> x1 u2) (setq kdk 0))
        )
        (progn
          (setq xc1 u1 yc1 (+ y1 (* (- u1 x1) al)))
          (if (> x2 u2)
            (setq xc2 u2 yc2 (+ y1 (* (- u2 x1) al)))
            (setq uc2 x2 vc2 (+ v1 (* (- x2 u1) be)))
          )
          (if (< x2 u1) (setq kdk 0))
        )
      )
      (if (> kdk 0)
        (progn
          (command "pline" (list xc1 yc1) (list xc2 yc2) (list uc2 vc2) (list uc1 vc1) "c" )
          (setq hinh (entlast))
          (ssadd hinh ss)
          (command "area" "e" hinh)
          (setq dtcon (getvar "AREA"))
          (setq dtl (+ dtl (- dtcon (* Hmat (- uc2 uc1)))))
        )
      )
      (setq j (1+ j))
    )
    (setq i (1+ i))
  )
  (command "erase" ss "")
  (setq dtl (/ (/ dtl he_so2) 2))
  (setq en (car (entsel "Thay cho so : ")))
  (setq elst (entget en))
  (setq elst (subst (cons 1 (strcat "" (rtos dtl 2 2))) (assoc 1 elst) elst))
  (entmod elst)
  (setvar "OSMODE" oslast)
  (setvar "CLAYER" lalast)
)
;=================================================
(defun c:AR2()
  (if (= Ty_le nil)
   (progn
   (initget (+ 1 2 4))
   (print)
   (print)
   (setq Ty_le (getreal "\nTy le : "))
   )
  )
  
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    ;;(setq vsize ( /(getvar "VIEWSIZE") 60 ))
    ;;(command "hatch" "ANSI31" vsize "0" "last" "")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
  (setq dtl (/ dtl 2.0))
  (setq en (car (entsel "Thay cho so : ")))
  (setq elst (entget en))
  (setq elst (subst (cons 1 (strcat "" (rtos dtl 2 2))) (assoc 1 elst) elst))
  (entmod elst)
;  (print)
;  (prompt (strcat "\nTotal area : " (rtos dtl 2 4)))
;  (print)
;  (setq pt2 (getpoint "\nPoint to write: "))
;  (command "text" pt2 (/ vsize 6) "0" (rtos dtl 2 2))
);defun
;=================================================

(defun c:00()
  (if (= Ty_le nil)
   (progn
   (initget (+ 1 2 4))
   (print)
   (print)
   (setq Ty_le (getreal "\nTy le : "))
   )
  )
  (setq en (car (entsel "Thay cho so : ")))
  (setq elst (entget en))
  (setq elst (subst (cons 1 (strcat "" (rtos 0 2 2))) (assoc 1 elst) elst))
  (entmod elst)
  (setvar "OSMODE" oslast)
  (setvar "CLAYER" lalast)
)
;=================================================
(defun C:HC ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.3))
  (command "layer" "s" "THKE" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
    (command "line" (list x1 y1) (list x2 y2) "")
    (setq pt1 pt2)
    (setvar "OSMODE" 33)
    (setq pt2 (getpoint "To : "))
  )
       ))
  (setq dthc (/ (/ dthc he_so2) 2))
  (setq en (car (entsel "Thay so dao dat huu co: ")))
  (setq elst (entget en))
  (setq elst (subst (cons 1 (strcat "" (rtos dthc 2 2))) (assoc 1 elst) elst))
  (entmod elst)
  (setq dtatb 0.00)
  (setvar "CLAYER" lalast)
;(command "AR2" "")
  )

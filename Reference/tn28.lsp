(prompt "n\n\ tnql28.lsp by CHIEN HUY")
(defun C:tl2 ()
    (initget (+ 1 2 4))
    (print)
    (print)
    (setq Ty_le (getreal "\nTy le : "))
)

(defun C:DB ()
  (if (= Ty_le nil)
    (progn
    (initget (+ 1 2 4))
    (print)
    (print)
    (setq Ty_le (getreal "\nTy le : "))
   )
  )
  (setq he_so (/ 1000.0 Ty_le))
  (setq he_so2 (* he_so he_so))
  (print)
  (setq eclast (getvar "CMDECHO"))
  (setq lalast (getvar "CLAYER"))
  (setq oslast (getvar "OSMODE"))
  (setvar "CMDECHO" 0)
  (setvar "OSMODE" 0)
  (command "-layer" "s" 6 "")
  (setq i "1 : " c 1.0)
  (setq s 0)
  (repeat 2
    (print)
    (setq e (entget (car (entsel (strcat "Taluy" i) ))))
    (if (/= e nil) (progn
    (setq pt1 (cdr (assoc 10  e)) pt2 (cdr (assoc 11 e)))
    (setq x1 (car pt1)  y1  (cadr pt1))
    (setq x2 (car pt2)  y2  (cadr pt2))

    (if (< y2  y1)  (progn
      (setq  x7 x1  y7 y1)
      (setq  x1 x2  y1 y2)
      (setq  x2 x7  y2 y7) 
                     ))
    (setq els (entget (car (entsel "Gioi han " ))))
    (setq pt3 (cdr (assoc 10 els)) pt4 (cdr (assoc 11 els)))
    (setq x3 (car pt3)  y3  (cadr pt3))
    (setq x4 (car pt4)  y4  (cadr pt4))

    (if (< y4  y3)  (progn
      (setq  x7 x3  y7 y3)
      (setq  x3 x4  y3 y4)
      (setq  x4 x7  y4 y7) 
                    ))
      
      (setq x7  (+ x1 (* c  4.50694)))
      (setq x8 (+ x7 (* c  4)) y8 (+ y1 2))
      (setq x9 (+ x3 (* c  100)) y9 (+ y3 2))

      (setq pt6 (inters (list x7 y1) (list x8 y8)  (list x3 y3) (list x9  y9) nil ))
      (setq x6 (car pt6)  y6  (cadr pt6))
   
      (command "line" (list (+ x1 (* c 4.50694)) y1) (list x6 y6) "" )
     
     (setq s1 (/ (+  4.5069  (* c (- x6 x3)))  2 ))
     (setq s1 (* (/ s1 he_so2) (- y3 y1))) 
     (setq s (+ s s1))
      ))
    (setq i "2 :"  c  -1.0) 
      )
  (print s)
 ;;  (setq ss (ssget))
 ;;  (setq u 0)
 ;;  (while (< u (sslength ss))
 ;;  (print u)
 ;;  (setq en (ssname ss u))
 ;; (setq elst (entget en))
 ;;  (setq loai (cdr (assoc 0 elst)))
 ;;  (if (= loai "TEXT")
 ;;    (progn
 ;;    (setq kh (cdr (assoc 1 elst)))
 ;;    (if (= kh "FF")
 ;;      (progn
 ;;      (print elst)    
 ;;      (setq elst (subst (cons 1  (rtos s 2 2)) (assoc 1 elst) elst)) 
 ;;      (entmod elst)
 ;;      ))
  ;;    )) 
  ;; (setq u (+ u 1))  
  ;; )
  (setq en (car (entsel "Thay so dat dap bao : ")))
  (setq elst (entget en))
  (setq elst (subst (cons 1  (rtos s 2 2)) (assoc 1 elst) elst)) 
  (entmod elst)
  (command "change" en "" "p" "layer"  6 "" "")  
  (setvar "OSMODE" oslast)
  (setvar "CLAYER" lalast)
  (setvar "CMDECHO" eclast)
)
(defun C:HVB ()
  (if (= Ty_le nil)
    (progn
    (initget (+ 1 2 4))
    (print)
    (print)
    (setq Ty_le (getreal "\nTy le : "))
    )
  )
  (setq he_so (/ 1000.0 Ty_le))
  (setq Dzlast (getvar "DIMZIN"))
  (setq eclast (getvar "CMDECHO"))
  (setq lalast (getvar "CLAYER"))
  (setq oslast (getvar "OSMODE"))
  (setvar "CMDECHO" 0)
  (setvar "DIMZIN" 0)
  (setvar "OSMODE" 1)
  (command "layer" "s" "0" "")
  (setq ptc (osnap (getpoint "\nDiem chuan : ") "end"))
  (setq yc (cadr ptc))
  (initget (+ 1 4))
  (setq Hc (getreal "Cao do : "))
   (setvar "OSMODE" 35)
   (setq ptb (getpoint "\nDay lop bun : "))
   (while (/= ptb nil)
    (setq xb (car ptb) yb (cadr ptb))
    (setq Hb (+ Hc (/ (- yb yc) he_so)))
    (setvar "OSMODE" 0)
    (setq pt (getpoint "\nNoi ghi cao do : "))
    (setq xt (car pt) yt (cadr pt))
    (if (> xt xb) (setq dx 2) (setq dx -2))
    (command "line" (list (+ xt 7) yt) pt (list xt yb) "")
    (command "line" ptb (list (+ xt dx) yb) "")
    (setq ytg (+ yb 1.732) xtt (- xt 1) xtp (+ xt 1))
    (command "line" (list xt yb) (list xtt ytg) (list xt ytg) "")
    (command "solid" (list xt yb) (list xtp ytg) (list xt ytg) "" "")
    (command "text" (list (+ xt 0.5) (+ yt 1)) 2 0 (rtos Hb 2 2))
    (setvar "OSMODE" 35)
    (setq ptb (getpoint "\nDay lop bun : "))
  )
  (setvar "OSMODE" oslast)
  (setvar "DIMZIN" Dzlast)
  (setvar "CLAYER" lalast)
  (setvar "CMDECHO" eclast)
)
(defun C:HC ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.2))
  (command "layer" "s" "1" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
    (command "line" (list x1 y1) (list x2 y2) "")
    (setq pt1 pt2)
    (setvar "OSMODE" 33)
    (setq pt2 (getpoint "To : "))
  )
       ))
  (setq dthc (/ (/ dthc he_so2) 1))
  (setq en (car (entsel "Thay so dao dat huu co: ")))
  (setq elst (entget en))
  (setq elst (subst (cons 1  (rtos dthc 2 2)) (assoc 1 elst) elst))
  (entmod elst)
  (setq dtatb 0.00)
  (setvar "CLAYER" lalast)
 ;;(command "mm" "")
)


(defun C:bb ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.07))
  (command "layer" "s" 6 "")
  (setvar "OSMODE" 35)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
   ;;(command "line" (list x1 y1) (list x2 y2) "")
    (setq pt1 pt2)
    (setvar "OSMODE" 35)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
;;  (command "line" (list x1 y1) (list x2 y2) "")
    (setq pt1 pt2)
    (setvar "OSMODE" 35)
    (setq pt2 (getpoint "To : "))
  )
       ))
  (setq dthc ( / dthc he_so2 ))
  (setq en (car (entsel "Thay so ATB: ")))
  (setq elst (entget en))
  (setq elst (subst (cons 1 (rtos dthc 2 2)) (assoc 1 elst) elst))
  (entmod elst)
  (command "change" en "" "p" "layer"  7 "" "")  
;;(setq en (car (entsel "Thay so bu lun da dam: ")))
  (setq elst (entget en))
  (setq elst (subst (cons 1 (rtos dthc 2 2)) (assoc 1 elst) elst))
  (entmod elst) 
  (command "change" en "" "p" "layer"  7 "" "")  
  (setq dtatb 0.00)
  (setvar "CLAYER" lalast)
)

(defun C:SD ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.30))
  (command "layer" "s" 7 "")
  (setvar "OSMODE" 35)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
   ;;(command "line" (list x1 y1) (list x2 y2) "")
    (setq pt1 pt2)
    (setvar "OSMODE" 35)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
;;  (command "line" (list x1 y1) (list x2 y2) "")
    (setq pt1 pt2)
    (setvar "OSMODE" 35)
    (setq pt2 (getpoint "To : "))
  )
       ))
  (setq dthc ( / dthc he_so2 ))
  (setq en (car (entsel "Thay so cpsd: ")))
  (setq elst (entget en))
  (setq elst (subst (cons 1 (rtos dthc 2 2)) (assoc 1 elst) elst))
  (entmod elst)
  (command "change" en "" "p" "layer"  7 "" "")  
;;(setq en (car (entsel "Thay so bu lun da dam: ")))
  (setq elst (entget en))
  (setq elst (subst (cons 1 (rtos dthc 2 2)) (assoc 1 elst) elst))
  (entmod elst) 
  (command "change" en "" "p" "layer"  7 "" "")  
  (setq dtatb 0.00)
  (setvar "CLAYER" lalast)
)

(defun C:VB ()
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sx he_so)
  (setq sy he_so)
  (setvar "OSMODE" 33)
  (command "-layer" "s" 1 "")
  (setq dy (* 0.8 sy))
  (setq pt1 (getpoint "\nDiem bat dau ben trai: "))
      (if (/= pt1 nil) (progn
   (setq pt2 (getpoint "diem cuoi : "))
    (if (/= pt2 nil) (progn
    (setq y1 (- (cadr pt1) dy) x1 (car pt1))
    (setq x2 (car pt2) y2 (cadr pt2))
    (setq ptl (getpoint "\n Chan taluy: "))
    (setq y1 (- y1 (* 0.02 (- x1 (car ptl)))))
    (setq x1 (car ptl))
    (setq pt1 (list x1 y1))
    (setq pt3 (list (- x1 2) (+ y1 2) ))
    (setq pt4 (list (- x2 2)  (- y2 2)))
    (setq els (entget (car (entsel "Gioi han 1:"))))
    (setq pt5 (cdr (assoc 10 els)) pt6 (cdr (assoc 11 els)))
    (setq pt7 (inters pt1 pt3  pt5 pt6 nil))
    (setq pt8 (inters pt2 pt4 pt1 (list (+ x1 100) (+ y1 2)) nil ))
    (setvar "OSMODE" 0)
    (command "line" pt7 pt1 pt8 pt2 "@-4,2" "")
    (setq pt1 pt2)
       ))
  ))
  (setvar "OSMODE" 33)
  (setq pt1 (getpoint "\nDiem bat dau ben phai: "))
      (if (/= pt1 nil) (progn
    (setq pt2 (getpoint "To : "))
    (if (/= pt2 nil) (progn
    (setq y1 (- (cadr pt1) dy) x1 (car pt1))
    (setq x2 (car pt2) y2 (cadr pt2))
    (setq ptl (getpoint "\n Chan taluy: "))
    (setq y1 (- y1 (* 0.02 (- (car ptl) x1) )))
    (setq x1 (car ptl))
    (setq pt1 (list x1 y1))
    (setq pt3 (list (+ x1 2) (+ y1 2) ))
    (setq pt4 (list (+ x2 2)  (- y2 2)))
    (setq els (entget (car (entsel "Gioi han 1:"))))
    (setq pt5 (cdr (assoc 10 els)) pt6 (cdr (assoc 11 els)))
    (setq pt7 (inters pt1 pt3  pt5 pt6 nil))
    (setq pt8 (inters pt2 pt4 pt1 (list (- x1 100) (+ y1 2)) nil))
    (setvar "OSMODE" 0)
    (command "line" pt7 pt1 pt8 pt2 "@4,2" "")
    (setq pt1 pt2)
       ))
  ))
  (setvar "OSMODE" oslast)
  (setvar "CLAYER" lalast)
  (setvar "CMDECHO" eclast)
)

(defun C:VB2 ()
  (if (= Ty_le nil)
    (progn
    (initget (+ 1 2 4))
    (print)
    (print)
    (setq Ty_le (getreal "\nTy le : "))
    )
  )
  (setq he_so (/ 1000.0 Ty_le))
  (print)

  (setq eclast (getvar "CMDECHO"))
  (setq lalast (getvar "CLAYER"))
  (setq oslast (getvar "OSMODE"))
  (setvar "CMDECHO" 0)
  (setq sx he_so)
  (setq sy he_so)
  (setvar "OSMODE" 33)
  (setq Dvb (* 0.60 sy))
  (setq ptd  (getpoint "From <end of> : "))
  (initget (+ 1 4))
  (setq xd (car ptd) yd (cadr ptd))
  (print)
  (setq ptc (getpoint "To <end of> : "))
  (setq xc (car ptc) yc (cadr ptc))
  (setq yvb (- (min yd yc) Dvb))
  (if (> xc xd) (setq dx 30.0) (setq dx -30.0))
  (setq x1 (- xd dx) y1 (+ yvb 15.0))
  (setq x2 (+ xc dx) y2 (+ yvb 15.0))
  (setq pt1 (list x1 y1) ptd (list xd yvb) ptc (list xc yvb) pt2 (list x2 y2))
  (command "-layer" "s" "THKE" "")
  (setvar "OSMODE" 0)
  (command "line" pt1 ptd ptc pt2 "")
  (setvar "OSMODE" oslast)
  (setvar "CLAYER" lalast)
  (setvar "CMDECHO" eclast)
)
(defun C:TD ()
  (if (= Ty_le nil)
    (progn
    (initget (+ 1 2 4))
    (print)
    (print)
    (setq Ty_le (getreal "\nTy le : "))
    )
  )
  (setq he_so (/ 1000.0 Ty_le))
  (print)

  (setq eclast (getvar "CMDECHO"))
  (setq lalast (getvar "CLAYER"))
  (setq oslast (getvar "OSMODE"))
  (setvar "CMDECHO" 0)
  (setq sy he_so)
  (setq Bx (* sy 6.5))
  (command "-layer" "s" "THKE" "")
  (setvar "OSMODE" 1)
  (setq pt1 (getpoint "Mep 1 : "))
  (setq x1 (car pt1)  y1 (cadr pt1))
  (setq pt2 (getpoint "Mep 1 : "))
  (setq x2 (car pt2) y2 (cadr pt2))
  (setq dx (/ (- Bx (- x2 x1)) 2.0))
  (setq dy (* dx 0.03))
  (setq xm1 (- x1 dx) ym1 (- y1 dy))
  (setq xc1 (- xm1 20.0) yc1 (- ym1 10.0))
  (setq xm2 (+ x2 dx) ym2 (- y2 dy))
  (setq xc2 (+ xm2 20.0) yc2 (- ym2 10.0))
  (setvar "OSMODE" 0)
  (command "line" (list xc1 yc1) (list xm1 ym1) pt1 pt2 (list xm2 ym2) (list xc2 yc2) "")
  (setvar "OSMODE" oslast)
  (setvar "CLAYER" lalast)
  (setvar "CMDECHO" eclast)
)
(defun C:GH ()
  (vmon)
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sy he_so)
  (command "layer" "s" 0 "")
  (setvar "osmode" 512)
  (print)
  (print)
  (setq pt (getpoint "\nDiem goc toa do <nearest to> : "))
  (setq yo (cadr pt))
  (setq y2 (- yo 10))
  (setq y1 (- y2 5))
  (setq y3 (+ y2 9))
  (setvar "osmode" 1)
  (setq pt (getpoint "\nDiem chuan <end of)        : ") )
  (setq yc (cadr pt))
 
      (setq en1 (car (entsel "Chon so cao do: ")))
      (setq elst1 (entget en1))
      (setq chso1 (cdr (assoc 1 elst1)))
      (setq hc (atof (substr chso1 1)))     
   
  (setq dy (- (* sy hc) yc))
  (print)
  (print)
  (setvar "osmode" 33)
  (setq pt (getpoint "\nDiem : "))
  (while (/= pt nil)
    (setq x (car pt) y (cadr pt))
    (setq h (/ (+ y dy) sy))
    (setq x1 (+ x 1))
    (setvar  "osmode" 0)
    (command "line" (list x y1) (list x y2) "")
    (command "line" (list x yo) (list x y) "")
    (command "text" "r" (list x y3) 1.8 90 (rtos h 2 2))
    (setvar "osmode" 33)
    (print)
    (print)
    (setq pt (getpoint "\nDiem : "))
  )
  (setvar "OSMODE" oslast)
  (setvar "CLAYER" lalast)
  (setvar "CMDECHO" eclast)

  ;;(setvar "OSMODE" 0)
)
;*
;*
(defun C:GL ()
  (if (= Ty_le nil)
    (progn
    (initget (+ 1 2 4))
    (print)
    (print)
    (setq Ty_le (getreal "\nTy le : "))
    )
  )
  (setq he_so (/ 1000.0 Ty_le))
  (print)

  (setq eclast (getvar "CMDECHO"))
  (setq lalast (getvar "CLAYER"))
  (setq oslast (getvar "OSMODE"))
  (setvar "CMDECHO" 0)
  (setq sx he_so)
  (setq lmin4 (/ 5.0 sx))	
  (setq lmin3 (/ 4.0 sx))
  (setq lmin1 (/ 1.5 sx))
  (command "layer" "s" 0 "")
  (command "osnap" "nearest")
  (print)
  (print)
  (setq pt (osnap (getpoint "\nNoi ghi cu ly <nearest to> : ") "nearest"))
  (setq y1 (cadr pt))
  (setq y2 (+ y1 5.0))
  (setq yc (+ y1 2.5))
  (print)
  (print)
  (setvar "OSMODE" 33)
  (setq pt (getpoint "\nTu diem <end,intersection of> : "))
  (while (/= pt nil)
    (setq x1 (car pt))
    (setq pt (getpoint "  Den diem <end,intersection of> : "))
    (setvar "OSMODE" 0)
    (setq x2 (car pt))
    (if (< x2 x1) (progn
      (setq xg x2)
      (setq x2 x1)
      (setq x1 xg)
      )
    )
    (setq dx (- x2 x1))
    (setq xt (/ dx sx))
    (setq sxt (rtos xt 2 2))
    (if (> xt 0.1) (progn
      ;;(setq kt " ")
      ;(while (= kt " ")
      ; (setq kk (substr sxt 1 1))
      ;  (if (= kk " ") (setq sxt (substr sxt 2)))
      ; (setq kt kk)
      ; )
      ;(setq len (strlen sxt))
      ;(setq kt (substr sxt len 1))
      ;;(while (= kt "0")
      ;;  (setq len (- len 1))
      ;;  (setq sxt (substr sxt 1 len))
      ;;  (setq kt (substr sxt len 1))
      ;;)
      ;;(if (= kt ".") (progn
      ;;  (setq len (- len 1))
      ;;  (setq sxt (substr sxt 1 len))
      ;;  )
      ;;)
      (setq len (strlen sxt))
      (setq xg (/ (+ x1 x2) 2.0))
      (setq x1 (+ x1 0.5))
      (setq x2 (- x2 0.5))
      (setq len1 -1)
      (if (> len 3) (setq len1 1))
      (if (= len 2) (setq len1 1))
      (if (> len1 0) (progn

      (if (< xt lmin3) (command "text"  "m" (list xg (+ yc 0) )  1.5  90  sxt)
        (command "text" "m" (list xg yc) 1.8 0 sxt)
        )

                      )
      )
      (if (= len 3) (progn
        (if (< xt lmin3) (command "text" "m" (list xg (+ yc 0) ) 1.5  90  sxt)
        (command "text" "m" (list xg yc) 2 0 sxt)
        )
        )
      )
      (if (= len 1) (progn
        (if (< xt lmin1) (command "text" "f" (list x1 yc) (list x2 yc) 2 sxt)
        (command "text" "m" (list xg yc) 2 0 sxt)
        )
        )
      )
      )
    )
    (setvar "OSMODE" 33)
    (print)
    (print)
    (setq pt (getpoint "\nTu diem <end of> : "))
  )
  (setvar "OSMODE" oslast)
  (setvar "CLAYER" lalast)
  (setvar "CMDECHO" eclast)
)
(defun C:vv ()
   
  (if (= Ty_le nil) (progn
    (setq Ty_le (getreal "\nDrawing scale : "))
                     )
 )
  (setq he_so (/ 1000 Ty_le))
  (setq he_so2 (* he_so he_so))
  (initget (+ 1  2  4))
 (setq lop (getint "n\lop: "))
 ;; (setq lop 2)
  (if (= lop 1) (setq Hmat (* 0.05 he_so)))
  (if (= lop 2) (setq Hmat (* 0.35 he_so)))
::(if (= lop 3) (setq Hmat (* 0.35 he_so)))
  (setq Hmat (* 0.05 he_so))
  (setq Hao (* 0.35 he_so))
  (setq lalast (getvar "CLAYER"))
  (setq oslast (getvar "OSMODE"))
  (setq settk (ssadd))
  (setq settn (ssadd))
  (setq ss (ssget))
  (setq c 0)
  (setq xmin 9000000 xmax -9000000)
  (setvar "OSMODE" 0)
  (while (< c (sslength ss))
    (setq en (ssname ss c))
    (setq elst (entget en))
    (setq loai (cdr (assoc 0 elst)))
    (if (= loai "LINE")
      (progn
        (setq pt1 (cdr (assoc 10 elst)) pt2 (cdr (assoc 11 elst)))
        (setq x1 (car pt1) x2 (car pt2))
        (if (> (abs (- x2 x1)) 0.001)
          (progn
            (setq la (cdr (assoc 8 elst)))
            (if (= la "1")(ssadd en settk))
            (if (= la "3")
              (progn
                (ssadd en settn)
                (if (< (min x1 x2) xmin) (setq xmin (min x1 x2)))
                (if (> (max x1 x2) xmax) (setq xmax (max x1 x2)))
              )
            )
          )
        )
      )
    )
    (setq c (1+ c))
  )
  (setq ss (ssadd))
  (setq cpddmr 0.24)
  (setq cpsdmr 0.51)
  (setq i 0 dtl 0.0)
  (while (< i (sslength settk))
    (setq en (ssname settk i))
    (setq elst (entget en))
    (setq pt1 (cdr (assoc 10 elst)))
    (setq pt2 (cdr (assoc 11 elst)))
    (setq x1 (car pt1) x2 (car pt2))
    (if (< x2 x1)
      (progn
      (setq p pt2)
      (setq pt2 pt1)
      (setq pt1 pt)
      )
    )
    (setq x1 (car pt1) y1 (cadr pt1))
    (setq x2 (car pt2) y2 (cadr pt2))
    (setq al (/ (- y2 y1) (- x2 x1)))
    (setq xd1 x1 yd1 (- y1 Hao) xd2 x2 yd2 (- y2 Hao) kdk 1)
    (if (and (< x1 xmin) (> x2 xmax))
      (progn
        (setq ud1 xmin vd1 (+ yd1 (* al (- xmin x1))))
        (setq ud2 xmax vd2 (+ yd1 (* al (- xmax x1))))
        (setq cpddmr (* (* 0.2 (- ud1 xd1)) he_so2))
        (setq cpddmr (+ cpddmr (* (* 0.2 (- xd2 ud2)) he_so2))) 
        (setq cpsdmr (* (* 0.3 (- ud1 xd1)) he_so2))
        (setq cpsdmr (+ cpsdmr (* (* 0.3 (- xd2 ud2)) he_so2))) 

    ;;(command "line" (list xd1 yd1) (list ud1 vd1) (list ud1 (+ vd1 3.9)) "")
     ;;(command "line" (list xd2 yd2) (list ud2 vd2) (list ud2 (+ vd2 3.9)) "")
      )
      (progn
        (if (and (> x1 xmin) (< x1 xmax)) (setq xd1 xmax yd1 (+ yd1 (* al (- xmax x1)))))
        (if (and (> x2 xmin) (< x2 xmax)) (setq xd2 xmin yd2 (+ yd1 (* al (- xmin x1)))))
        (if (and (> x1 xmin) (< x2 xmax)) (setq kdk 0))
         (command "layer" "s" "1" "")
        (if (> kdk 0) (command "line" (list xd1 yd1) (list xd2 yd2) ""))
        (setq cpddmr (+ cpddmr (* (/ (- xd2 xd1) he_so) 0.2)))
        (setq cpsdmr (+ cpsdmr (* (/ (- xd2 xd1) he_so) 0.3)))
        (command "layer" "s" 6 "")

        (if (and (> x1 xmin) (< x1 xmax)) 
          (progn
         ;; (command "line" (list xd1 yd1) "@0,3.9" "")
         ;; (command "line" (list xd2 yd2) "@0,3.9" "")
         ;; (command "line" (list xd2 (+  yd2 3.45)) "@16.7606,0.1676" "")
         ;; (command "line" (list xd2 (+ 2.5 yd2)) (list (- xd2 30) (+ 2.5 (- yd2 (* 30 al)))) "")

          ))
        (if (and (> x2 xmin) (< x2 xmax) ) 
          (progn
          ;;(command "line" (list xd2 yd2) "@0,3.9" "" )
          ;;(command "line" (list xd1 yd1) "@0,3.9" "")
          ;;(command "line" (list xd1 (+  yd1 3.45)) "@-16.7606,0.1676" "")
          ;;(command "line" (list xd1 (+ 2.5 yd1)) (list (+ xd1 30) ( + (+ yd1 2.5) (* 30 al))) "")
          ))

      )
    )
    (setq j 0)
    (while (< j (sslength settn))
      (setq en (ssname settn j))
      (setq elst (entget en))
      (setq qt1 (cdr (assoc 10 elst)))
      (setq qt2 (cdr (assoc 11 elst)))
      (setq u1 (car qt1) u2 (car qt2))
      (if (< u2 u1)
        (progn
          (setq p qt2)
          (setq qt2 qt1)
          (setq qt1 p)
        )
      )
      (setq u1 (car qt1) v1 (cadr qt1))
      (setq u2 (car qt2) v2 (cadr qt2))
      (setq be (/ (- v2 v1) (- u2 u1)))
      (setq p1 pt1 p2 pt2 q1 qt1 q2 qt2 kdk 1)
      (setq xc1 x1 yc1 y1 xc2 x2 yc2 y2)
      (setq uc1 u1 vc1 v1 uc2 u2 vc2 v2)
      (if (> x1 u1)
        (progn
          (setq uc1 x1 vc1 (+ v1 (* (- x1 u1) be)))
          (if (< x2 u2)
            (setq uc2 x2 vc2 (+ v1 (* (- x2 u1) be)))
            (setq xc2 u2 yc2 (+ y1 (* (- u2 x1) al)))
          )
          (if (> x1 u2) (setq kdk 0))
        )
        (progn
          (setq xc1 u1 yc1 (+ y1 (* (- u1 x1) al)))
          (if (> x2 u2)
            (setq xc2 u2 yc2 (+ y1 (* (- u2 x1) al)))
            (setq uc2 x2 vc2 (+ v1 (* (- x2 u1) be)))
          )
          (if (< x2 u1) (setq kdk 0))
        )
      )
      (if (> kdk 0)
        (progn
          (command "pline" (list xc1 yc1) (list xc2 yc2) (list uc2 vc2) (list uc1 vc1) "c" )
          (setq hinh (entlast))
          (ssadd hinh ss)
          (command "area" "e" hinh)
          (setq dtcon (getvar "AREA"))
          (setq dtl (+ dtl (- dtcon (* Hmat (- uc2 uc1)))))
        )
      )
      (setq j (1+ j))
    )
    (setq i (1+ i))
  )
  (command "erase" ss "")
  (setq dtl (/ dtl he_so2) )
  (if (= lop 1) (setq en (car (entsel "Thay cho so bv BTNM: "))))
  (if (= lop 2) (setq en (car (entsel "Thay cho so bv CPDD: "))))
  ::(if (= lop 3) (setq en (car (entsel "Thay cho so bv CPDD: "))))
  (setq elst (entget en))
  (setq elst (subst (cons 1  (rtos dtl 2 2)) (assoc 1 elst) elst))
  (entmod elst)
  (command "change" en "" "p" "layer"  6 "" "")  
  (setq en (car (entsel "Thay cho so CPDD MR: ")))
  (setq elst (entget en))
  (setq elst (subst (cons 1 (rtos cpddmr 2 2)) (assoc 1 elst) elst))
  (entmod elst)
  (command "change" en "" "p" "layer"  6 "" "")  
  (setq en (car (entsel "Thay cho so CPSD MR: ")))
  (setq elst (entget en))
  (setq elst (subst (cons 1  (rtos cpsdmr 2 2)) (assoc 1 elst) elst))
  (entmod elst)
  (command "change" en "" "p" "layer"  6 "" "")  
  (setvar "OSMODE" oslast)
  (setvar "CLAYER" lalast)
) 

(defun c:MM()
  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en (car (entsel "Thay cho so : ")))
  (setq elst (entget en))
  (setq elst (subst (cons 1 (rtos dtl 2 2)) (assoc 1 elst) elst))
  (entmod elst)
  (command "change" en "" "p" "layer"  7 "" "")  
;  (print)
;  (prompt (strcat "\nTotal area : " (rtos dtl 2 2)))
;  (print)
;  (setq pt2 (getpoint "\nPoint to write: "))
;  (command "text" pt2  "0" "2" (rtos dtl 4 2))
);defun
(defun C:DA ()
  (if (= Ty_le nil)
    (progn
    (initget (+ 1 2 4))
    (print)
    (print)
    (setq Ty_le (getreal "\nTy le : "))
    )
  )
  (setq he_so (/ 1000.0 Ty_le))
  (print)
  (setq lalast (getvar "CLAYER"))
  (setq oslast (getvar "OSMODE"))
  (setvar "osmode" 33) 

  (setq s 0.0)
  (setq pt1 (getpoint "Bat dau ben trai : "))
  (if (/= pt1 nil) (progn
  (setq pt2 (getpoint "To : "))
  (while (/= pt2 nil)
    (setq s (+ s (distance pt1 pt2)))
    (setq pt1 pt2)
    (setq pt2 (getpoint "To : "))
  )
  ))
  (if (/= s 0) (setq s (+ (/ s he_so) 0)))
  
  (setq s2 0.0)
  (setq pt1 (getpoint "Bat dau ben phai : "))
  (if (/= pt1 nil) (progn
  (setq pt2 (getpoint "To : "))
  (while (/= pt2 nil)
    (setq s2 (+ s2 (distance pt1 pt2)))
    (setq pt1 pt2)
    (setq pt2 (getpoint "To : "))
  )
  ))                
 (if (/= s2 0) (setq s2 (+ (/ s2 he_so) 0)))
  (setq s (+ s s2))

  (setq en (car (entsel "Thay cho so : ")))
  (setq elst (entget en))
  (setq elst (subst (cons 1  (rtos s 2 2)) (assoc 1 elst) elst))
  (entmod elst)

  (command "change" en "" "p" "layer"  0 "" "")  

  (command "setvar" "OSMODE" oslast)

)

(defun C:VA ()
  (if (= Ty_le nil)
    (progn
    (initget (+ 1 2 4))
    (print)
    (print)
    (setq Ty_le (getreal "\nTy le : "))
    )
  )
  (setq he_so (/ 1000.0 Ty_le))
  (print)
  (setq lalast (getvar "CLAYER"))
  (setq oslast (getvar "OSMODE"))
  (setvar "osmode" 33) 

  (setq s 0.0)
  (setq pt1 (getpoint "Bat dau ben trai : "))
  (if (/= pt1 nil) (progn
  (setq pt2 (getpoint "To : "))
  (while (/= pt2 nil)
    (setq s (+ s (distance pt1 pt2)))
    (setq pt1 pt2)
    (setq pt2 (getpoint "To : "))
  )
  ))
  (if (/= s 0) (setq s (+ (/ s he_so) 1.0)))
  
  (setq s2 0.0)
  (setq pt1 (getpoint "Bat dau ben phai : "))
  (if (/= pt1 nil) (progn
  (setq pt2 (getpoint "To : "))
  (while (/= pt2 nil)
    (setq s2 (+ s2 (distance pt1 pt2)))
    (setq pt1 pt2)
    (setq pt2 (getpoint "To : "))
  )
  ))                
 (if (/= s2 0) (setq s2 (+ (/ s2 he_so) 1.0)))
  (setq s (+ s s2))

  (setq en (car (entsel "Thay cho so VDKT: ")))
  (setq elst (entget en))
  (setq elst (subst (cons 1  (rtos s 2 2)) (assoc 1 elst) elst))
  (entmod elst)

  (command "change" en "" "p" "layer"  6 "" "")  
;  (print)
;  (prompt (strcat "\nChieu dai : " (rtos s 2 2)))
;  (print)
   (command "setvar" "OSMODE" oslast)

)

(defun C:GG ()
  (if (= Ty_le nil)
    (progn
    (initget (+ 1 2 4))
    (print)
    (print)
    (setq Ty_le (getreal "\nTy le : "))
    )
  )
  (setq he_so (/ 1000.0 Ty_le))
  (setq Dzlast (getvar "DIMZIN"))
  (setq eclast (getvar "CMDECHO"))
  (setq lalast (getvar "CLAYER"))
  (setq oslast (getvar "OSMODE"))
  (setvar "CMDECHO" 0)
  (setvar "DIMZIN" 0)
  (setvar "OSMODE" 1)
  (command "layer" "s"  7 "")
    (if (= yc nil) (progn
  (setq ptc (getpoint "\nDiem chuan : ") ) 
  (setq yc (cadr ptc))
  (initget (+ 1 4))
  (setq hc (getreal "Cao do : "))
                   )
    )
   (setvar "OSMODE" 35)
   (setq ptb (getpoint "\nDiem ghi : "))
   (while (/= ptb nil)
    (setq xb (car ptb) yb (cadr ptb))
    (setq Hb (+ Hc (/ (- yb yc) he_so)))
    (setvar "OSMODE" 0)
    (setq pt (getpoint "\nNoi ghi cao do : "))
    (setq xt (car pt) yt (cadr pt))
    (if (> xt xb) (setq dx  2) (setq  dx -2)) 
    (if (> xt xb)  (command "line" (list (+ xt 7) yt) pt (list xt yb) "")
    (command "line" (list (- xt 8) yt) pt (list xt yb) "")
    )
    (command "line" ptb (list (+ xt dx) yb) "")
    (setq xtt (- xt  1) xtp (+ xt   1) )
    (if (> yt yb) (setq ytg (+ yb 1.732)))
    (if (< yt yb) (setq ytg (- yb 1.732))) 
    (command "line" (list xt yb) (list xtt ytg) (list xt ytg) "")
    (command "solid" (list xt yb) (list xtp ytg) (list xt ytg) "" "")
    (setq height 1.6) ;;(* 1.6 he_so))
    (setq st1 (rtos Hb 2 2))   
    (if (> Hb 0) (setq st1 (strcat "+" st1)))
     (if (> xt xb) (command "text" (list (+ xt 1) (+ yt 0.5))   height   0  st1 )
     (command "text" (list (- xt 8) (+ yt 0.5))   height   0  st1 )
     )
    (setvar "OSMODE" 33)
    (setq ptb (getpoint "\ndiem ghi : "))
  )
  (setvar "OSMODE" oslast)
  (setvar "DIMZIN" Dzlast)
  (setvar "CLAYER" lalast)
  (setvar "CMDECHO" eclast)
)
(defun C:hh ()
  (setq oslast (getvar "OSMODE"))
  (setq lalast (getvar "clayer"))
  (setvar "OSMODE" 1)
  (setq ptc (getpoint "\nDiem chuan <end of> : "))
  (setq yc (cadr ptc))
  (initget (+ 1 4))
  (setq hc (getreal "\nCao do : "))
  ;;(setq hc 2.5)
  (setq dy (- (* hc ym) yc))
  (print)
  (setvar "osmode" oslast)
 )
(defun C:KK ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.57))
  (command "layer" "s" "THKE" "")
  (setvar "OSMODE" 33)
  (setq dthc 0)
  (setq pt1 (getpoint "\nDiem bat dau: "))
      (if (/= pt1 nil) (progn
  (setq pt2 (getpoint "Diem tiep theo : "))
    (setq y1 (- (cadr pt1) dy) x1 (car pt1))
    (setq y2 (- (cadr pt2) dy) x2 (car pt2))
    (setq dtt (abs (* dy (- x2 x1))))
    (setq dthc (+ dthc dtt))
    (setvar "OSMODE" 0)
  
       ))
  (setq dthc (/ (+ (/ dthc he_so2) 0.3) 2))
  (setq en (car (entsel "Thay so kcmd: ")))
  (setq elst (entget en))
  (setq elst (subst (cons 1 (strcat ": " (rtos dthc 2 2))) (assoc 1 elst) elst))
  (entmod elst)
  (setq dtatb 0.00)
  (setvar "CLAYER" lalast)
 ;;(command "mm" "")
)
(defun C:ss ()
  (setq dzlast (getvar "DIMZIN"))
  (setvar "DIMZIN" 0)
  (setq en1 (car (entsel "\n SO THU NHAT: ")))
  (while (/= en1 nil)
    (setq en2 (car (entsel "\n SO THU HAI : ")))
    (command "change" en1 en2 "" "p" "layer" 7 "" "")
    (setq elst1 (entget en1))
    (setq chso1 (cdr (assoc 1 elst1)))
    (setq so1 (atof (substr chso1 1)))
    (setq elst2 (entget en2))
    (setq chso2 (cdr (assoc 1 elst2)))
    (setq so2 (atof (substr chso2 1)))
    (setq so2 (+ so2 so1))
    ;;(setq so1 (* so1 2))
    ;;(setq elst1 (subst (cons 1 (strcat ": " (rtos so1 2 2))) (assoc 1 elst1) elst1))
    ;;(entmod elst1)
    (setq elst2 (subst (cons 1 (rtos so2 2 2)) (assoc 1 elst2) elst2))
    (entmod elst2)
    (setq en1 (car (entsel "\n SO THU NHAT: ")))
  )
  (setvar "DIMZIN" dzlast)
)

(defun C:tt ()
  (setq dzlast (getvar "DIMZIN"))
  (setvar "DIMZIN" 0)
  (setq en1 (car (entsel "\n SO THU NHAT: ")))
  (while (/= en1 nil)
    (setq en2 (car (entsel "\n SO THU HAI : ")))
    (command "change" en1 en2 "" "p" "layer" 7 "" "")
    (setq elst1 (entget en1))
    (setq chso1 (cdr (assoc 1 elst1)))
    (setq so1 (atof (substr chso1 1)))
    (setq elst2 (entget en2))
    (setq chso2 (cdr (assoc 1 elst2)))
    (setq so2 (atof (substr chso2 1)))
    (setq so2 (- so2 so1))
    ;;(setq so1 (* so1 2))
    ;;(setq elst1 (subst (cons 1 (strcat ": " (rtos so1 2 2))) (assoc 1 elst1) elst1))
    ;;(entmod elst1)
    (setq elst2 (subst (cons 1 (rtos so2 2 2)) (assoc 1 elst2) elst2))
    (entmod elst2)
    (setq en1 (car (entsel "\n SO THU NHAT: ")))
  )
  (setvar "DIMZIN" dzlast)
)



(defun C:ttt ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.03))
  (setq dy1 (* he_so 0.03))
  (command "layer" "s" 6 "")
  (setvar "OSMODE" 33)

  (setq pt1 (getpoint "\nDiem bat dau : "))
      (if (/= pt1 nil) (progn
  (setq pt2 (getpoint "To : "))
  (if (/= pt2 nil)
    (progn 
    (setq y1 (- (cadr pt1) dy) x1 (car pt1))
    (setq y2 (- (cadr pt2) dy) x2 (car pt2))
    (setq dtt (abs (* dy (- x2  x1))))
    (setq dtt1 (abs (* dy1 (- x2 x1))))
   ;(setq dtac 1.40 )
   ;;(setq dtatb (- 2.03  (/ dtt1 he_so2)) )
    (setvar "OSMODE" 0)
   ;;(command "line" (list x1 y1) (list x2 y2) "")
    (setvar "OSMODE" 33)
  ))
       ))

 ;(setq en (car (entsel "Thay cho so AC: ")))
 ;(setq elst (entget en))
 ;(setq elst (subst (cons 1 (rtos dtac 2 2)) (assoc 1 elst) elst))
 ;(entmod elst)
 ;(command "change" en "" "p" "layer"  6 "" "")  
  (setq en (car (entsel "Thay so ATB: ")))
  (setq elst1 (entget en))
  (setq chuso (cdr (assoc 1 elst1)))
  (setq so (atof (substr chuso 1)))
  (setq dtatb (- so (/ dtt he_so2)) )  
  (setq elst1 (subst (cons 1 (rtos dtatb 2 2)) (assoc 1 elst1) elst1))
  (entmod elst1) 
  (command "change" en "" "p" "layer"  7 "" "")  

  ;;(setq en (car (entsel "Thay so BU VENH ATB: ")))
  ;;(setq elst (entget en))
  ;;(setq chso (cdr (assoc 1 elst)))
  ;;(setq sobv (atof (substr chso 1)))
  ;;(setq sobv (+ sobv  (/ dtt1 he_so2)) )
  ;;(setq elst (subst (cons 1 (rtos sobv 2 2)) (assoc 1 elst) elst))
  ;;(entmod elst) 
  ;;(command "change" en "" "p" "layer"  6 "" "")  



  (setq dtatb 0.00)
  (setq dtac 0.00)
  (setvar "CLAYER" lalast)
  (setvar "osmode" oslast)
)

(defun c:MMm()
  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (command "layer" "f" "5" "")
 ;;(command "layer" "f" "6" "")


  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)

    (setq pt1 (getpoint "\nPick internal point : "))
  )
  (command "setvar" "OSMODE" oslast)
  (command "erase" ss "")
  (setq ss nil)
  (command "redraw")
  (setq dtl (/ dtl tl2))
  (setq en (car (entsel "Thay cho so : ")))
  (setq elst (entget en))
  (setq elst (subst (cons 1 (rtos dtl 2 2)) (assoc 1 elst) elst))
  (entmod elst)
  (command "change" en "" "p" "layer"  7 "" "")  
 (command "layer" "t" "5" "")
 ;; (command "layer" "t" "6" "")

);defun

(defun c:ad()
  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en1 (car (entsel "Thay so CAN CONG THEM: ")))
 
  (setq elst1 (entget en1))
  (setq chso1 (cdr (assoc 1 elst1)))
  (setq so1 (atof (substr chso1 1)))
  (setq so1 (+ dtl so1))
  (setq elst1 (subst (cons 1 (rtos so1 2 2)) (assoc 1 elst1) elst1))
  (entmod elst1)
  (command "change" en1 "" "p" "layer"  7 "" "")  
  
   (setq en2 (car (entsel "\n Thay so TRU BOT : ")))
       
    (setq elst2 (entget en2))
    (setq chso2 (cdr (assoc 1 elst2)))
    (setq so2 (atof (substr chso2 1)))
    (setq so2 (- dtl so2))
    (setq so2 (- so2))
    (setq elst2 (subst (cons 1 (rtos so2 2 2)) (assoc 1 elst2) elst2))
    (entmod elst2)
    (command "change" en2 "" "p" "layer"  7 "" "")  
   
;  (print)
;  (prompt (strcat "\nTotal area : " (rtos dtl 2 2)))
;  (print)
;  (setq pt2 (getpoint "\nPoint to write: "))
;  (command "text" pt2  "0" "2" (rtos dtl 4 2))
);defun

(defun c:SUB()
  (if (= Ty_le nil)
    (progn
    (initget (+ 1 2 4))
    (print)
    (print)
    (setq Ty_le (getreal "\nTy le : "))
    )
  )
  (setq ntl (/ 1000.0 Ty_le))
  (setq tl2 (* ntl ntl))
  (print)

  (setq dtl 0)
  (setq ss (ssadd))
  (setq oslast (getvar "OSMODE"))
  (command "osnap" "")
  (print)
  (print)
  (setq pt1 (getpoint "\nPick internal point : "))
  (while (/= pt1 nil)
    (command "-boundary" pt1 "")
    (setq et (entlast))
    (ssadd et ss)
    (command "area" "e" "last")
    (command "hatch" "ANSI31" 4 "0" "last" "")
    (setq et (entlast))
    (ssadd et ss)
    (setq dtcon (getvar "AREA"))
    (setq dtl (+ dtcon dtl))
    (print)
    (print)
    (setq pt1 (getpoint "\nPick internal point : "))
  )
  (command "setvar" "OSMODE" oslast)
  (command "erase" ss "")
  (setq ss nil)
  (command "redraw")
  (setq dtl (/ dtl tl2))
;;(setq dtl (/ dtl 2.0))
  (prompt (strcat "\nTotal area : " (rtos dtl 2 2)))
  (PRINT)
  (setq en1 (car (entsel "Thay so cong: ")))
  (setq elst1 (entget en1))
  (setq chso1 (cdr (assoc 1 elst1)))
  (setq so1 (atof (substr chso1 1)))
  (setq so1 (- so1 dtl))
  (setq elst1 (subst (cons 1 (rtos so1 2 2)) (assoc 1 elst1) elst1))
  (entmod elst1)

  (setq en2 (car (entsel "\n Thay so kq : ")))
    ;;(command "change" en1 en2 "" "p" "layer" 6 "" "")
    (setq elst2 (entget en2))
    (setq chso2 (cdr (assoc 1 elst2)))
    (setq so2 (atof (substr chso2 1)))
    (setq so2 so1)
    (setq elst2 (subst (cons 1 (rtos so2 2 2)) (assoc 1 elst2) elst2))
    (entmod elst2)

   (command "change" en2 "" "p" "layer"  7 "" "")  
;  (print)
;  (prompt (strcat "\nTotal area : " (rtos dtl 2 2)))
;  (print)
;  (setq pt2 (getpoint "\nPoint to write: "))
;  (command "text" pt2  "0" "2" (rtos dtl 4 2))
);defun

(defun C:add ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.2))
  (command "layer" "s" "2" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) dy) x1 (car pt1))
    (setq y2 (- (cadr pt2) dy) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
    (setq y1 (- (cadr pt1) dy) x1 (car pt1))
    (setq y2 (- (cadr pt2) dy) x2 (car pt2))
    (setq dtp (abs (* dy (- x2 x1))))
    (setq dthc (+ dthc dtp))
    (setvar "OSMODE" 0)
    (command "line" (list x1 y1) (list x2 y2) "")
    (setq pt1 pt2)
    (setvar "OSMODE" 33)
    (setq pt2 (getpoint "To : "))
  )
       ))
  (setq dthc (/ (/ dthc he_so2) 1))
  (setq en (car (entsel "Thay so dao dat : ")))
  (setq elst (entget en))
  (setq chso (cdr (assoc 1 elst)))
  (setq so1 (atof (substr chso 1)))
  (setq so1 (+ so1 dthc))
  (setq elst (subst (cons 1  (rtos so1 2 2)) (assoc 1 elst) elst))
  (entmod elst)

  (setq en2 (car (entsel "Thay so dap dat : ")))
  (setq elst2 (entget en2))
  (setq chso2 (cdr (assoc 1 elst2)))
  (setq so2 (atof (substr chso2 1)))
  (setq so2 (+ so2 dthc))
  (setq elst2 (subst (cons 1  (rtos so2 2 2)) (assoc 1 elst2) elst2))
  (entmod elst2)

  (setq dtatb 0.00)
  (setvar "CLAYER" lalast)
 ;;(command "mm" "")
)

(defun C:tc ()
  (vmon)
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sy he_so)
  (command "layer" "s" 1 "")
  (setvar "osmode" 33)
  (print)
  (print)
  (setq pt1 (getpoint "\nChan tuong : "))
    (setq x1 (car pt1) y1 (cadr pt1) )

    (setvar "osmode" 0)
   (setvar "osmode" 512)
  (print)
  (print)
    (setq els (entget (car (entsel "Gioi han " ))))
    (setq pt3 (cdr (assoc 10 els)) pt4 (cdr (assoc 11 els)))
    (setq x3 (car pt3)  y3  (cadr pt3))
    (setq x4 (car pt4)  y4  (cadr pt4))

    (setq  y2  (+ y1 2) )

      (setq pt5 (inters (list x3 y3) (list x4 y4)  (list x1 y1) (list x1  y2) nil ))
      (setq x5 (car pt5)  y5  (cadr pt5))

    (command "line" (list x1 y1 ) (list x5 (+ y5 0)) "")
    (command "text"  (list x1 (+ y5 4) )  2.0  90 "TC" "")
    (print)
    (print)

  (setvar "OSMODE" oslast)
  (setvar "CLAYER" lalast)
  (setvar "CMDECHO" eclast)

  ;;(setvar "OSMODE" 0)
)

(defun C:tn ()
  (if (= Ty_le nil)
    (progn
    (initget (+ 1 2 4))
    (print)
    (print)
    (setq Ty_le (getreal "\nTy le : "))
    )
  )
  (setq he_so (/ 1000.0 Ty_le))
  (print)
  (setq eclast (getvar "CMDECHO"))
  (setq lalast (getvar "CLAYER"))
  (setq oslast (getvar "OSMODE"))
  (setvar "CMDECHO" 0)
  (setq sx he_so)
  (setq sy he_so)
  (setvar "OSMODE" 33)
  (command "-layer" "s" 1 "")
  (setq dy (* 1.2 sy))

(setvar "osmode" 512)
  (print)
  (print)
  (setq pt (getpoint "\nChan duong dong <nearest to> : "))
  (setq y0 (cadr pt))
  (setq yg1 (- y0 1))
  (setq yg2 (- y0 10))
  (setq yg3 (- y0 12.5))
  (setq yg4 (- y0 15))

  (setq kt 0)  

  (setvar "OSMODE" 33)
  (setq pt1 (getpoint "\nDiem bat dau ben trai: "))
      
  (if (/= pt1 nil) (progn
    (setq y1 (cadr pt1) x1 (car pt1))
    
   (setq en1 (car (entsel "Chon so cao do: ")))
   (setq elst1 (entget en1))
   (setq chso1 (cdr (assoc 1 elst1)))
   (setq hc (atof (substr chso1 1)))
   (setq dty (- (* sy hc) y1))

    (print)
    (setq kt 1)  

    (setq x2 (- x1 dy) y2 (+ y1 dy ) )
    (setq pt2 (list  x2  y2) )
    (setq h2 (/ (+ y2 dty) sy))

    (setq ll (getreal "\n Chieu dai mo rong: "))
    (setq x3 (- x2  (* ll sx)) y3 (+ y2 (* ll 0.03)) )
    (setq pt3 (list  x3  y3) )
    (setq x4 (- x3 2) y4 (+ y3 2)  )
    (setq pt4 (list  x4  y4 ) )
    (setq h3 (/ (+ y3 dty) sy))
    
     
   (setq els (entget (car (entsel "Gioi han 1:"))))
    (setq pt5 (cdr (assoc 10 els)) pt6 (cdr (assoc 11 els)))
    (setq pt7 (inters pt3 pt4  pt5 pt6 nil))
    (setq y7 (cadr pt7)    x7 (car pt7) )
    (setq h7 (/ (+ y7 dty) sy))
    (setvar "OSMODE" 0)
    (if (> ll 0) (command "line" pt1 pt2 pt3 pt7 ""))
    (if (= ll 0) (command "line" pt1  pt7 ""))                
   
    (command "-layer" "s" 7 "")

    (if (> ll 0) (progn 
    (command "line" pt2 (list x2 y0) "")
    (command "line" (list x2  yg2) (list x2 yg4 ) "")
    (command "text" "r" (list x2 yg1) 1.8 90 (rtos h2 2 2))
      ))
    
    (if (> ll 0) (progn 
    (command "line" pt3 (list x3 y0) "")
    (command "line" (list x3  yg2) (list x3 yg4 ) "")
    (command "text" "r" (list x3 yg1) 1.8 90 (rtos h3 2 2))
     ))

    (command "line" pt7 (list x7 y0) "")
    (command "line" (list x7  yg2) (list x7 yg4 ) "")
    (command "text" "r" (list x7 yg1) 1.8 90 (rtos h7 2 2))   
  
    (setq dx (- x1 x2))
    (setq xt (/ dx sx))
    (setq xg (* 0.5 (+ x1 x2)) )
    (setq sxt (rtos xt 2 2))
     (if (> ll  0) (command "text" "m" (list xg yg3) 1.8 0 sxt) )
                   
     
    (setq dx (- x2 x3))
    (setq xt (/ dx sx))
    (setq xg (*  0.5 (+ x2 x3)) )
    (setq sxt (rtos xt 2 2))
    
    (if (> ll  0) (command "text" "m" (list xg yg3) 1.8 0 sxt))
                  

    (if (> ll 0) (Progn
    (setq dx (- x3 x7))
    (setq xt (/ dx sx))
    (setq xg (*  0.5 (+ x3 x7)) )
                 ))
    (if (= ll 0) (Progn
    (setq dx (- x1 x7))
    (setq xt (/ dx sx))
    (setq xg (*  0.5 (+ x1 x7)) )
                 ))
    
    (setq sxt (rtos xt 2 2))

    (command "text" "m" (list xg yg3) 1.8 0 sxt)
 

   ))

(setvar "OSMODE" 33)
(setq pt1 (getpoint "\nDiem bat dau ben phai: "))
      
  (if (/= pt1 nil) (progn
      (if (= kt 0) (progn
   (setq y1 (cadr pt1) x1 (car pt1))
      (setq en1 (car (entsel "Chon so cao do: ")))
      (setq elst1 (entget en1))
      (setq chso1 (cdr (assoc 1 elst1)))
      (setq hc (atof (substr chso1 1)))     

      (setq dty (- (* sy hc) y1))

       (print)   
       )) 


    (setq x2 (+ x1 dy) y2 (+ y1 dy ) )
    (setq pt2 (list  x2  y2) )
    (setq h2 (/ (+ y2 dty) sy))
   
    (setq ll (getreal "\n Chieu dai mo rong: "))
    (setq x3 (+ x2  (* ll sx)) y3 (+ y2 (* ll 0.03)) )
    (setq pt3 (list  x3  y3) )
    (setq pt4 (list  (+ x3 2) (+ y3 2) ) )
    (setq h3 (/ (+ y3 dty) sy))

    (setq els (entget (car (entsel "Gioi han 1:"))))
    (setq pt5 (cdr (assoc 10 els)) pt6 (cdr (assoc 11 els)))
    (setq pt7 (inters pt3 pt4  pt5 pt6 nil))
    (setq y7 (cadr pt7)    x7 (car pt7) )
    (setq h7 (/ (+ y7 dty) sy))
    (setvar "OSMODE" 0)
    (command "-layer" "s" 1 "")
    (if (> ll 0) (command "line" pt1 pt2 pt3 pt7 ""))
    (if (= ll 0)            
    (command "line" pt1  pt7 ""))       
    

    (command "-layer" "s" 7 "")
       (if (> ll 0) (progn
    (command "line" pt2 (list x2 y0) "")
    (command "line" (list x2  yg2) (list x2 yg4 ) "")
    (command "text" "r" (list x2 yg1) 1.8 90 (rtos h2 2 2))
                    ))

         (if (> ll 0) (progn
    
    (command "line" pt3 (list x3 y0) "")
    (command "line" (list x3  yg2) (list x3 yg4 ) "")
    (command "text" "r" (list x3 yg1) 1.8 90 (rtos h3 2 2))
                       ))

    (command "line" pt7 (list x7 y0) "")
    (command "line" (list x7  yg2) (list x7 yg4 ) "")
    (command "text" "r" (list x7 yg1) 1.8 90 (rtos h7 2 2))   
  
    (setq dx (- x2 x1))
    (setq xt (/ dx sx))
    (setq xg (*  0.5 (+ x1 x2)) )
    (setq sxt (rtos xt 2 2))
       
    (if (> ll 0 ) 
    (command "text" "m" (list xg yg3) 1.8 0 sxt))

    (setq dx (- x3 x2))
    (setq xt (/ dx sx))
    (setq xg (*  0.5 (+ x2 x3)) )
    (setq sxt (rtos xt 2 2))
       (if (> ll 0 )  (command "text" "m" (list xg yg3) 1.8 90 sxt)) 
       
       (if (> ll 0 ) (Progn
    (setq dx (- x7 x3))
    (setq xt (/ dx sx))
    (setq xg (*  0.5 (+ x3 x7)) )
                     
                     ) (Progn
    (setq dx (- x7 x1))
    (setq xt (/ dx sx))
    (setq xg (*  0.5 (+ x1 x7)) )
                     ))
    
       
(setq sxt (rtos xt 2 2))
      
    (command "text" "m" (list xg yg3) 1.8 0 sxt)
    

    
  ))


  (setvar "OSMODE" oslast)
  (setvar "CLAYER" lalast)
  (setvar "CMDECHO" eclast)
)

(defun C:sss ()
  (setq dzlast (getvar "DIMZIN"))
  (setvar "DIMZIN" 0)
  (setq AA (getreal "\nSo cong: "))
  (setq en1 (car (entsel "\n SO CONG THEM: ")))
  (while (/= en1 nil)
   
    (setq elst1 (entget en1))
    (setq chso1 (cdr (assoc 1 elst1)))
    (setq so1 (atof (substr chso1 6)))
    (setq so1 (+ AA so1))
    
    (setq elst1 (subst (cons 1 (strcat "KM65+ " (rtos so1 2 2))) (assoc 1 elst1) elst1))
    (entmod elst1)
    
    (setq en1 (car (entsel "\n SO CONG THEM: ")))
  )
  (setvar "DIMZIN" dzlast)
)
(defun C:kl ()
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy1 (* he_so 0.05))
  (setq dy2 (* he_so 0.2))
  (command "layer" "s" "1" "")
  (setvar "OSMODE" 33)
  (setq BTNT 0)
  (setq CPDD 0)
  (setq pt1 (getpoint "\nDiem bat dau ben trai: "))
      (if (/= pt1 nil) (progn
  (setq pt2 (getpoint "To : "))
  (while (/= pt2 nil)
    (setq x1 (car pt1))
    (setq  x2 (car pt2))
    (setq dtt1 (abs (* dy1 (- x2 x1))))
    (setq dtt2 (abs (* dy2 (- x2 x1))))
    
    (setq BTNT (+ BTNT dtt1))
    (setq CPDD (+ CPDD dtt2))
    
    (setvar "OSMODE" 0)
    ;;(command "line" (list x1 y1) (list x2 y2) "")
    (setq pt1 pt2)
    (setvar "OSMODE" 33)
    (setq pt2 (getpoint "To : "))
  )
       ))
  (setq pt1 (getpoint "\nDiem bat dau ben phai: "))
      (if (/= pt1 nil) (progn
  (setq pt2 (getpoint "To : "))
  (while (/= pt2 nil)
  (setq x1 (car pt1))
    (setq  x2 (car pt2))
    (setq dtt1 (abs (* dy1 (- x2 x1))))
    (setq dtt2 (abs (* dy2 (- x2 x1))))
     
    (setq BTNT (+ BTNT dtt1))
    (setq CPDD (+ CPDD dtt2))
    
    (setvar "OSMODE" 0)
    ;;(command "line" (list x1 y1) (list x2 y2) "")
    (setq pt1 pt2)
    (setvar "OSMODE" 33)
    (setq pt2 (getpoint "To : "))
  )
  ))
  (setq BTNT (/ (/ BTNT he_so2) 1))
  (setq CPDD (/ (/ CPDD he_so2) 1))

 
  (setq en (car (entsel "Thay so BTNT: ")))
  (setq elst (entget en))
  (setq elst (subst (cons 1  (rtos BTNT 2 2)) (assoc 1 elst) elst))
  (entmod elst)
  
  (setq en1 (car (entsel "Thay so CPDD: ")))
    (setq elst (entget en1))
    (setq elst (subst (cons 1  (rtos CPDD 2 2)) (assoc 1 elst) elst))
  (entmod elst)
  
      
  (setq dtatb 0.00)
  (setvar "CLAYER" lalast)
 
)
(defun C:W ()
 
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.12))
  (command "layer" "s" "2" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) 0.85) x1 (car pt1))
    (setq y2 (- (cadr pt2) 0.85) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  
    (setq dthc (/ (/ dthc he_so2) 1))
    
    (setq en1 (car (entsel "Thay so bi tru: ")))
    (setq elst1 (entget en1))
    (setq chso1 (cdr (assoc 1 elst1)))
    (setq so1 (atof (substr chso1 1)))
    (setq so1 (- so1 dthc))
    (setq elst1 (subst (cons 1  (rtos so1 2 2)) (assoc 1 elst1) elst1))
    (entmod elst1)
    
    (setq en2 (car (entsel "Thay so cong vao: ")))
        (setq elst2 (entget en2))
        (setq chso2 (cdr (assoc 1 elst2)))
        (setq so2 (atof (substr chso2 1)))
        (setq so2 (+ so2 dthc))
        (setq elst2 (subst (cons 1  (rtos so2 2 2)) (assoc 1 elst2) elst2))
    (entmod elst2)
    (command "change" en1 EN2 "" "p" "layer" 7 "" "")
    
  (setvar "CLAYER" lalast)
 ;;(command "mm" "")
)
(defun C:WW()
 
   (if (= Ty_le nil)  (setq Ty_le (getreal "\nDrawing scale : ")))
   (setq he_so (/ 1000 Ty_le))
   (setq he_so2 (* he_so he_so))
   (setq lalast (getvar "CLAYER"))
  (setq oslast (getvar "OSMODE"))
  (setq dy (* he_so 0.18))
  (command "layer" "s" "2" "")
  (setvar "OSMODE" 33)
  (setq dthc 0)
  (setq pt1 (getpoint "\nDiem bat dau ben trai: "))
      (if (/= pt1 nil) (progn
  (setq pt2 (getpoint "To : "))
  (while (/= pt2 nil)
    (setq y1 (- (cadr pt1) 0.9) x1 (car pt1))
    (setq y2 (- (cadr pt2) 0.9) x2 (car pt2))
    (setq dtt (abs (* dy (- x2 x1))))
    (setq dthc (+ dthc dtt))
    (setvar "OSMODE" 0)
    (command "line" (list x1 y1) (list x2 y2) "")
    (setq pt1 pt2)
    (setvar "OSMODE" 33)
    (setq pt2 (getpoint "To : "))
  )
       ))
  
    (setq dthc (/ (/ dthc he_so2) 1))
    
    (setq en1 (car (entsel "Thay so bi tru: ")))
    (setq elst1 (entget en1))
    (setq chso1 (cdr (assoc 1 elst1)))
    (setq so1 (atof (substr chso1 1)))
    (setq so1 (- so1 dthc))
    (setq elst1 (subst (cons 1  (rtos so1 2 2)) (assoc 1 elst1) elst1))
    (entmod elst1)
    
    (setq en2 (car (entsel "Thay so cong vao: ")))
        (setq elst2 (entget en2))
        (setq chso2 (cdr (assoc 1 elst2)))
        (setq so2 (atof (substr chso2 1)))
        (setq so2 (+ so2 dthc))
        (setq elst2 (subst (cons 1  (rtos so2 2 2)) (assoc 1 elst2) elst2))
    (entmod elst2)
     (command "change" en1 EN2 "" "p" "layer" 7 "" "")     
  
  (setvar "CLAYER" lalast)
 ;;(command "mm" "")
)

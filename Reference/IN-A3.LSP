(defun c:ve ()
(setq oslast (getvar "osmode"))
(setvar "osmode" 33) 
(setq pt1 (getpoint "n\Start point : "))
(setq lap (getint  "n\number of drawings :")) 
(setvar "osmode" 0)
(setq x1 (car pt1) y1 (cadr pt1) )
(setq  y2  (+ y1 285) )

(Repeat lap
(setq pt1 (list x1 y1))
(setq x2  (+ x1 400))
(setq pt2 (list x2 y2))
(command "_plot" "y"  "" "" "" "M" "" "" "w" pt1  pt2  "" "" "" "" "" "" "" "" "") 
(setq x1 (+ x1  440) )
 )

(setvar "osmode" oslast)  
)


(defun c:ve2 ()
(setq pt1 (getpoint "n\Start point : "))
(setq x1 (car pt1) y1 (cadr pt1) )
(setq x2 16000)
(setq y2 (+ y1 281.5))
(setvar "osmode" 0)
 (while (< x1  x2) 
(setq ss (ssget  "W"  (list (+ x1 10) y1) (list (+ x1 440) y2)))
(if (/= ss nil) (progn
(setq pt1 (list x1  y1) pt2 (list (+ x1 385.5) y2))
(setq pt4 (list x1 (- y1 300)) pt5 (list (+ x1 385.5) (- y1 8.5)))
;;(setq pt3 (list xkd ykd))
;;(command "INSERT"  "kt"  pt3  "" "" "")
(command "_plot" "y"  "" "" "" "" "" "" "w" pt1  pt2  "" "" "") 
(command "_plot" "y"  "" "" "" "" "" "" "w" pt4  pt5  "" "" "") 
               )
)
(setq x1 (+ x1  440) )
 ) 
)

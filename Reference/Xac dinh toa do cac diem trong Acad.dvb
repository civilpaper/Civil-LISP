Attribute VB_Name = "FrmNhap"
Attribute VB_Base = "0{6462F30B-0C19-4028-8701-CF827CAF025C}{A7AFDE84-3E05-4B37-84CD-B256ED46CAF7}"
Attribute VB_GlobalNameSpace = False
Attribute VB_Creatable = False
Attribute VB_PredeclaredId = True
Attribute VB_Exposed = False
Attribute VB_TemplateDerived = False
Attribute VB_Customizable = False
Private Sub XuLyBanPhim(ByRef KeyAscii, ByVal Txt As String, ByVal CheckDauCham As Boolean)
Dim i As Byte
    Select Case KeyAscii
        Case Asc("0") To Asc("9"), 8, 127       '   Backspace, Delete
        Case Asc(".")
            If CheckDauCham Then
                For i = 1 To Len(Txt)
                    If Mid(Txt, i, 1) = "." Then
                        KeyAscii = 0
                        Beep
                        Exit For
                    End If
                Next i
            Else
                KeyAscii = 0
                Beep
            End If
        Case Else
            KeyAscii = 0
            Beep
    End Select
End Sub

Private Sub OptionAcad_Click()
    TxtW_Cot.Enabled = True
    TxtH_Hang.Enabled = True
'    Label11.Enabled = True
'    TxtTyleXuat.Enabled = True
End Sub

Private Sub OptionExcel_Click()
    TxtW_Cot.Enabled = False
    TxtH_Hang.Enabled = False
'    Label11.Enabled = False
'    TxtTyleXuat.Enabled = False
End Sub

Private Sub UserForm_Initialize()
    Combo_DV.AddItem "mm"
    Combo_DV.AddItem "cm"
    Combo_DV.AddItem "m"
    Combo_DV.ListIndex = 1

    Combo_Sole.AddItem "0"
    Combo_Sole.AddItem "1"
    Combo_Sole.AddItem "2"
    Combo_Sole.AddItem "3"
    Combo_Sole.AddItem "4"
    Combo_Sole.ListIndex = 1

    TxtW_Cot.Enabled = False
    TxtH_Hang.Enabled = False
    Label_HeTrucToaDo.Caption = Label_hide.Caption & "1 : " & Chr(10) & "X O Y"
    TxtTyleVe.SelStart = 0
    TxtTyleVe.SelLength = Len(TxtTyleXuat.Text)
    TxtTyleVe.SetFocus
End Sub

Private Sub TxtTyleVe_KeyPress(ByVal KeyAscii As MSForms.ReturnInteger)
    XuLyBanPhim KeyAscii, TxtTyleVe.Text, True
End Sub

Private Sub TxtTyleVe_Change()
    Label_dvVe.Caption = Label_dv.Caption & TxtTyleVe.Text & "mm"
End Sub

Private Sub TxtTyleXuat_KeyPress(ByVal KeyAscii As MSForms.ReturnInteger)
    XuLyBanPhim KeyAscii, TxtTyleXuat.Text, True
End Sub

Private Sub TxtTyleXuat_Change()
    TxtW_Cot.Text = 17 * Val(TxtTyleXuat.Text)
    TxtH_Hang = 5 * Val(TxtTyleXuat.Text)
End Sub

Private Sub TxtW_Cot_KeyPress(ByVal KeyAscii As MSForms.ReturnInteger)
    XuLyBanPhim KeyAscii, TxtW_Cot.Text, True
End Sub

Private Sub TxtH_Hang_KeyPress(ByVal KeyAscii As MSForms.ReturnInteger)
    XuLyBanPhim KeyAscii, TxtH_Hang.Text, True
End Sub

Private Sub TxtTrucToaDo_Change()
    Label_Y.Caption = "Y" & TxtTrucToaDo.Text & " (CM)"
    Label_HeTrucToaDo.Caption = Label_hide.Caption & SLTrucToaDo & " : " & Chr(10) & _
                                                                    "X" & TxtTrucToaDo.Text & " O Y" & TxtTrucToaDo.Text
End Sub

Private Sub TxtVitri1_Change()
    Label_ViTri.Caption = TxtVitri1.Text & "2" & TxtVitri2.Text
End Sub

Private Sub TxtVitri2_Change()
    Label_ViTri.Caption = TxtVitri1.Text & "2" & TxtVitri2.Text
End Sub

Private Sub Combo_Sole_Change()
    If Combo_Sole.Value = 0 Then
        Lbl_1x.Caption = Int(Val(Lbl_1x.Caption))
        Lbl_1y.Caption = Int(Val(Lbl_1y.Caption))
        Lbl_2x.Caption = Int(Val(Lbl_2x.Caption))
        Lbl_2y.Caption = Int(Val(Lbl_2y.Caption))
    Else
        Lbl_1x.Caption = Int(Val(Lbl_1x.Caption)) & "." & String(Combo_Sole.Value, "0")
        Lbl_1y.Caption = Int(Val(Lbl_1y.Caption)) & "." & String(Combo_Sole.Value, "0")
        Lbl_2x.Caption = Int(Val(Lbl_2x.Caption)) & "." & String(Combo_Sole.Value, "0")
        Lbl_2y.Caption = Int(Val(Lbl_2y.Caption)) & "." & String(Combo_Sole.Value, "0")
    End If
End Sub

Private Sub Check_Stt_Click()
    If Check_Stt.Value = True Then
        Label5.Caption = "1"
        Label_ViTri.Caption = TxtVitri1.Text & "2" & TxtVitri2.Text
    Else
        Label5.Caption = i - 1
        Label_ViTri.Caption = TxtVitri1.Text & i & TxtVitri2.Text
    End If
End Sub

Private Sub NutOK_Click()
    If Val(TxtTyleVe.Text) = 0 Then
        TxtTyle.SetFocus
        Exit Sub
    End If
    If Val(TxtTyleXuat.Text) = 0 Then
        TxtTyle.SetFocus
        Exit Sub
    End If
    If Val(TxtW_Cot.Text) = 0 Then
        TxtW_Cot.SetFocus
        Exit Sub
    End If
    If Val(TxtH_Hang.Text) = 0 Then
        TxtH_Hang.SetFocus
        Exit Sub
    End If
    
    Me.Hide
End Sub

Private Sub NutCancel_Click()
    If SLTrucToaDo = 1 Then
        End
    Else
        CheckStop = True
        Me.Hide
    End If
End Sub

Attribute VB_Name = "Xac_dinh_toa_do"
' Macro recorded 10/10/2005 by Nguyen Van Diep, PTK1, Tedi South

Public SLTrucToaDo As Integer, i As Integer
Public CheckStop As Boolean
Type HeTrucToaDo
    TenXOY As String
    SoDiem As Integer
    TenViTri(0 To 50) As String
    ToadoX(0 To 50) As Double
    ToadoY(0 To 50) As Double
End Type
Dim HeTTD() As HeTrucToaDo


Sub XacDinhToaDo()
Dim TextObj As AcadText
Dim InsPt(0 To 2) As Double
Dim Pnt As Variant, P1 As Variant, P2 As Variant, P3 As Variant
Dim St1 As String, St2 As String, St3 As String
Dim Old_Osmode As Variant, Old_Ucsicon As Variant, Old_Pdmode As Variant
Dim TyleBV As Integer, TyleXuat As Integer
Dim Stt As Integer, j As Integer, m As Integer, i As Byte
Dim TextXoa() As AcadText
Dim PointXoa() As AcadCircle
Dim bankinh As Variant
Dim PolarPnt As Variant, Angle As Variant
Dim ErrNumber As Variant, KhoangCach As Double
Dim Txt_DonVi As String, Sochusole As Byte, SoChia As Integer


    Old_Osmode = ThisDrawing.GetVariable("OSMODE")
    Old_Ucsicon = ThisDrawing.GetVariable("UCSICON")
    Old_Pdmode = ThisDrawing.GetVariable("PDMODE")
    ThisDrawing.SetVariable "UCSFOLLOW", 0
    ThisDrawing.SetVariable "PDMODE", 35
    ThisDrawing.SendCommand "_ucsicon" & vbCr & "on" & vbCr
    ThisDrawing.SendCommand "_ucsicon" & vbCr & "or" & vbCr
    Load FrmNhap
    
    CheckStop = False
    InsPt(2) = 0
    i = 0   '   Dďng cho tŞn vŢ trÝ cńa ®iÓm
    Stt = 0 '   Dďng ®Ó x¸c ®Ţnh tćng sč ®iÓm ®­îc chän
    SLTrucToaDo = 0
    On Error Resume Next

    Do
        Err.Clear
        SLTrucToaDo = SLTrucToaDo + 1
        If SLTrucToaDo > 1 Then
            FrmNhap.TxtTyleVe.Enabled = False
            FrmNhap.Label_HeTrucToaDo.Caption = FrmNhap.Label_hide.Caption & SLTrucToaDo & " : " & Chr(10) & _
                                                                "X" & FrmNhap.TxtTrucToaDo.Text & " O Y" & FrmNhap.TxtTrucToaDo.Text
            FrmNhap.TxtTrucToaDo.SelStart = 0
            FrmNhap.TxtTrucToaDo.SelLength = Len(FrmNhap.TxtTrucToaDo.Text)
            FrmNhap.TxtTrucToaDo.SetFocus
            FrmNhap.Check_Stt.Visible = True
        End If

        FrmNhap.Show
        If CheckStop = True And SLTrucToaDo = 1 Then End
        ThisDrawing.SetVariable "PDSIZE", 0.4 * Val(FrmNhap.TxtTyleXuat.Text) / 10

        If CheckStop = False Then
            ReDim Preserve HeTTD(0 To SLTrucToaDo - 1) As HeTrucToaDo
            HeTTD(SLTrucToaDo - 1).TenXOY = FrmNhap.TxtTrucToaDo.Text
                
            If SLTrucToaDo > 1 Then
                ThisDrawing.SetVariable "OSMODE", 33                                '  ChŘ dďng bľt ®iÓm END vµ INT
                P1 = ThisDrawing.Utility.GetPoint(, "Chän t©m hÖ trôc täa ®é thř " & SLTrucToaDo & " (X" & _
                                HeTTD(SLTrucToaDo - 1).TenXOY & " O Y" & HeTTD(SLTrucToaDo - 1).TenXOY & ") : ")
                ThisDrawing.SetVariable "OSMODE", Old_Osmode          ' Tr¶ ląi c¸ch bľt ®iÓm cň
                If Err.Number = 0 Then
                    P1 = ThisDrawing.Utility.TranslateCoordinates(P1, acWorld, acUCS, False)
                    P2 = ThisDrawing.Utility.GetPoint(P1, "Chän 1 ®iÓm trŞn h­íng d­¬ng cńa trôc hoµnh (trôc Ox" & _
                                                                                                                                    HeTTD(SLTrucToaDo - 1).TenXOY & ") : ")
                    P3 = ThisDrawing.Utility.GetPoint(P1, "Chän 1 ®iÓm trŞm nöa mĆt phĽng X" & _
                                HeTTD(SLTrucToaDo - 1).TenXOY & " O Y" & HeTTD(SLTrucToaDo - 1).TenXOY & _
                                " (theo h­íng d­¬ng cńa trôc tung Oy" & HeTTD(SLTrucToaDo - 1).TenXOY & ") : ")
                    P2 = ThisDrawing.Utility.TranslateCoordinates(P2, acWorld, acUCS, False)
                    P3 = ThisDrawing.Utility.TranslateCoordinates(P3, acWorld, acUCS, False)
                    St1 = P1(0) & "," & P1(1) & "," & P1(2)
                    St2 = P2(0) & "," & P2(1) & "," & P2(2)
                    St3 = P3(0) & "," & P3(1) & "," & P3(2)
                    ThisDrawing.SendCommand "_ucs" & vbCr & "N" & vbCr & "3" & vbCr & St1 & vbCr & St2 & vbCr & St3 & vbCr
                Else
                    ReDim P1(0 To 2) As Double
                    P1(0) = 0
                    P1(1) = 0
                    P1(2) = 0
                    Err.Clear
                End If

                If FrmNhap.Check_Stt.Value = True Then
                    i = 0
                Else
                    i = i - 1
                End If
            Else
                ReDim P1(0 To 2) As Double
                P1(0) = 0
                P1(1) = 0
                P1(2) = 0
            End If
            
            j = 0   '   Dďng cho vßng lĆp
            Do
                i = i + 1
                j = j + 1
                Pnt = ThisDrawing.Utility.GetPoint(, "Chän ®iÓm thř " & FrmNhap.TxtVitri1.Text & i & _
                                                                                                                         FrmNhap.TxtVitri2.Text & " : ")
                If Err.Number = 0 Then
                    InsPt(0) = Pnt(0)
                    InsPt(1) = Pnt(1)
                    Pnt = ThisDrawing.Utility.TranslateCoordinates(Pnt, acWorld, acUCS, False)
                    HeTTD(SLTrucToaDo - 1).ToadoX(j - 1) = Pnt(0)
                    HeTTD(SLTrucToaDo - 1).ToadoY(j - 1) = Pnt(1)
                    HeTTD(SLTrucToaDo - 1).TenViTri(j - 1) = FrmNhap.TxtVitri1.Text & i & FrmNhap.TxtVitri2.Text
                    ReDim Preserve PointXoa(0 To Stt) As AcadCircle
                    ReDim Preserve TextXoa(0 To Stt) As AcadText
                    bankinh = Val(FrmNhap.TxtTyleXuat.Text) / 20
                    Set PointXoa(Stt) = ThisDrawing.ModelSpace.AddCircle(InsPt, bankinh)
'                    P1 = ThisDrawing.Utility.TranslateCoordinates(P1, acOCS, acWorld, False)
                    Angle = ThisDrawing.Utility.AngleFromXAxis(P1, InsPt)
                    PolarPnt = ThisDrawing.Utility.PolarPoint(InsPt, Angle, 1.5 * Val(FrmNhap.TxtTyleXuat.Text) / 10)
                    Set TextXoa(Stt) = ThisDrawing.ModelSpace.AddText(HeTTD(SLTrucToaDo - 1).TenViTri(j - 1), _
                                                                                                                                PolarPnt, 1.6 * Val(FrmNhap.TxtTyleXuat.Text) / 10)
                    TextXoa(Stt).Alignment = acAlignmentMiddleCenter
                    TextXoa(Stt).TextAlignmentPoint = PolarPnt
                    ErrNumber = Err.Number
                    TextXoa(Stt).Layer = "2"
                    TextXoa(Stt).StyleName = "3"
                    TextXoa(Stt).ScaleFactor = 0.7
                    TextXoa(Stt).Update
                    Err.Number = ErrNumber

                    Stt = Stt + 1
                End If
            Loop While Err.Number = 0
            HeTTD(SLTrucToaDo - 1).SoDiem = j - 1
        End If
    Loop Until CheckStop = True
    
    Err.Clear

    ThisDrawing.SendCommand "_ucs" & vbCr & vbCr
    
    Txt_DonVi = FrmNhap.Combo_DV.Value
    Sochusole = Val(FrmNhap.Combo_Sole.Value)
    Select Case Txt_DonVi
        Case "mm"
            SoChia = 1
        Case "cm"
            SoChia = 10
        Case "m"
            SoChia = 1000
    End Select
    
    On Error GoTo 0
    
    If SLTrucToaDo = 1 & i = 1 Then
        ThisDrawing.Utility.Prompt "      Bąn ch­a chän ®iÓm nµo, ch­¬ng tr×nh sĎ tho¸t ..."
        End
    End If
    
    TyleBV = Val(FrmNhap.TxtTyleVe.Text)
    
    If FrmNhap.OptionAcad.Value = True Then
        '   XuĘt qua Acad
        XuatAcad PointXoa, TextXoa, Txt_DonVi, Sochusole, SoChia, TyleBV
    Else
        '   XuĘt qua Excel
        XuatExcel PointXoa, TextXoa, Txt_DonVi, Sochusole, SoChia, TyleBV
    End If

    ThisDrawing.SetVariable "UCSICON", Old_Ucsicon
    ThisDrawing.SetVariable "PDMODE", Old_Pdmode
    Unload FrmNhap
End Sub


Sub XuatAcad(ByVal PointXoa, ByVal TextXoa, ByVal Txt_DonVi As String, ByVal Sochusole As Byte, _
                            ByVal SoChia As Integer, ByVal TyleBV As Integer)
Dim lineObj As AcadLine
Dim TextObj As AcadText
Dim Pt1(0 To 2) As Double
Dim Pt2(0 To 2) As Double
Dim InsPt(0 To 2) As Double
Dim basePnt As Variant
Dim TyleXuat As Integer, j As Integer

    TyleXuat = Val(FrmNhap.TxtTyleXuat.Text)
    
    On Error Resume Next
    
    basePnt = ThisDrawing.Utility.GetPoint(, "Chän ®iÓm bľt ®Çu vĎ : ")
    If FrmNhap.Check_Xoa.Value = True Then
        For i = 0 To UBound(PointXoa)
            PointXoa(i).Delete
            TextXoa(i).Delete
        Next i
    End If
    
    If Err.Number <> 0 Then End
     
     '   VĎ text "B¶NG TäA §é"
    InsPt(0) = basePnt(0) + Val(FrmNhap.TxtW_Cot.Text) * 3 * (SLTrucToaDo - 1) / 2
    InsPt(1) = basePnt(1)
    Set TextObj = ThisDrawing.ModelSpace.AddText("%%uBAŰNG TOĎA ŃOÄ", InsPt, 3.5 * TyleXuat)
    TextObj.Alignment = acAlignmentMiddleCenter
    TextObj.TextAlignmentPoint = InsPt
    TextObj.Layer = "0"
    TextObj.StyleName = "5"
    TextObj.Update
     
    basePnt(1) = basePnt(1) - 8 * TyleXuat
    Pt2(2) = 0
    j = 0   '   Sč thř tů hÖ trôc täa ®é
    Do
        j = j + 1
        
        '   VĎ ®­ęng thĽng n»m ngang trŞn cďng
        Pt1(0) = basePnt(0)
        Pt2(0) = basePnt(0) + Val(FrmNhap.TxtW_Cot.Text) * 3
        Pt1(1) = basePnt(1)
        Pt2(1) = Pt1(1)
        Set lineObj = ThisDrawing.ModelSpace.AddLine(Pt1, Pt2)
        lineObj.Layer = "0"
        lineObj.Update

        '   VĎ text "VŢ trÝ"
        InsPt(0) = basePnt(0) + Val(FrmNhap.TxtW_Cot.Text) / 2
        InsPt(1) = basePnt(1) - Val(FrmNhap.TxtH_Hang.Text) / 2
        Set TextObj = ThisDrawing.ModelSpace.AddText("VŇ TRÍ", InsPt, 1.6 * TyleXuat)
        TextObj.Alignment = acAlignmentMiddleCenter
        TextObj.TextAlignmentPoint = InsPt
        TextObj.Layer = "0"
        TextObj.StyleName = "3"
        TextObj.ScaleFactor = 1
        TextObj.Update

        '   VĎ text "X (CM)"
        InsPt(0) = basePnt(0) + Val(FrmNhap.TxtW_Cot.Text) * 1.5
        Set TextObj = ThisDrawing.ModelSpace.AddText("X" & HeTTD(j - 1).TenXOY & " (" & UCase(Txt_DonVi) & _
                                                                                                            ")", InsPt, 1.6 * TyleXuat)
        TextObj.Alignment = acAlignmentMiddleCenter
        TextObj.TextAlignmentPoint = InsPt
        TextObj.Layer = "0"
        TextObj.StyleName = "3"
        TextObj.ScaleFactor = 1
        TextObj.Update
        
        '   VĎ text "Y (CM)"
        InsPt(0) = basePnt(0) + Val(FrmNhap.TxtW_Cot.Text) * 2.5
        Set TextObj = ThisDrawing.ModelSpace.AddText("Y" & HeTTD(j - 1).TenXOY & " (" & UCase(Txt_DonVi) & _
                                                                                                            ")", InsPt, 1.6 * TyleXuat)
        TextObj.Alignment = acAlignmentMiddleCenter
        TextObj.TextAlignmentPoint = InsPt
        TextObj.Layer = "0"
        TextObj.StyleName = "3"
        TextObj.ScaleFactor = 1
        TextObj.Update

        Pt1(0) = basePnt(0)
        Pt2(0) = basePnt(0) + Val(FrmNhap.TxtW_Cot.Text) * 3

        i = 0       '   Sč thř tů ®iÓm
        Do
            i = i + 1
            '   VĎ ®­ęng thĽng n»m ngang
            Pt1(1) = basePnt(1) - i * Val(FrmNhap.TxtH_Hang.Text)
            Pt2(1) = Pt1(1)
            Set lineObj = ThisDrawing.ModelSpace.AddLine(Pt1, Pt2)
            If i = 1 Then
                lineObj.Layer = "0"
            Else
                lineObj.Layer = "1"
            End If
            lineObj.Update

            '   VĎ sč thř tů
            InsPt(0) = basePnt(0) + Val(FrmNhap.TxtW_Cot.Text) / 2
            InsPt(1) = basePnt(1) - (i + 0.5) * Val(FrmNhap.TxtH_Hang.Text)
            Set TextObj = ThisDrawing.ModelSpace.AddText(HeTTD(j - 1).TenViTri(i - 1), InsPt, 1.6 * TyleXuat)
            TextObj.Alignment = acAlignmentMiddleCenter
            TextObj.TextAlignmentPoint = InsPt
            TextObj.Layer = "2"
            TextObj.StyleName = "2"
            TextObj.ScaleFactor = 0.7
            TextObj.Update

            '   VĎ täa ®é X
            InsPt(0) = basePnt(0) + Val(FrmNhap.TxtW_Cot.Text) * 1.5
            Set TextObj = ThisDrawing.ModelSpace.AddText(Round(HeTTD(j - 1).ToadoY(i - 1) * TyleBV / SoChia, _
                                        Sochusole), InsPt, 1.6 * TyleXuat)
            TextObj.Alignment = acAlignmentMiddleCenter
            TextObj.TextAlignmentPoint = InsPt
            TextObj.Layer = "2"
            TextObj.StyleName = "2"
            TextObj.ScaleFactor = 0.7
            TextObj.Update

            '   VĎ täa ®é Y
            InsPt(0) = basePnt(0) + Val(FrmNhap.TxtW_Cot.Text) * 2.5
            Set TextObj = ThisDrawing.ModelSpace.AddText(Round(HeTTD(j - 1).ToadoX(i - 1) * TyleBV / SoChia, _
                                        Sochusole), InsPt, 1.6 * TyleXuat)
            TextObj.Alignment = acAlignmentMiddleCenter
            TextObj.TextAlignmentPoint = InsPt
            TextObj.Layer = "2"
            TextObj.StyleName = "2"
            TextObj.ScaleFactor = 0.7
            TextObj.Update

        Loop Until i = HeTTD(j - 1).SoDiem

        '   VĎ ®­ęng thĽng n»m ngang d­íi cďng
        Pt1(0) = basePnt(0)
        Pt2(0) = basePnt(0) + Val(FrmNhap.TxtW_Cot.Text) * 3
        Pt1(1) = basePnt(1) - (i + 1) * Val(FrmNhap.TxtH_Hang.Text)
        Pt2(1) = Pt1(1)
        Set lineObj = ThisDrawing.ModelSpace.AddLine(Pt1, Pt2)
        lineObj.Layer = "0"
        lineObj.Update

        '   VĎ c¸c ®­ęng thĽng ®řng
        Pt1(1) = basePnt(1)
        Pt2(1) = basePnt(1) - (i + 1) * Val(FrmNhap.TxtH_Hang.Text)
        
        m = 0
        Do
            m = m + 1
            Pt1(0) = basePnt(0) + (m - 1) * Val(FrmNhap.TxtW_Cot.Text)
            Pt2(0) = Pt1(0)
            Set lineObj = ThisDrawing.ModelSpace.AddLine(Pt1, Pt2)
            lineObj.Layer = "0"
            lineObj.Update
        Loop Until m = 4
        
        '   ChuČn bŢ cho vßng lĆp sau
        basePnt(0) = basePnt(0) + Val(FrmNhap.TxtW_Cot.Text) * 3
    Loop Until j = SLTrucToaDo - 1
End Sub


Sub XuatExcel(ByVal PointXoa, ByVal TextXoa, ByVal Txt_DonVi As String, ByVal Sochusole As Byte, _
                            ByVal SoChia As Integer, ByVal TyleBV As Integer)
Dim ExcelApp As Object, ExcelObj As Object
Dim j As Integer
    
    If FrmNhap.Check_Xoa.Value = True Then
        For i = 0 To UBound(PointXoa)
            PointXoa(i).Delete
            TextXoa(i).Delete
        Next i
    End If

    On Error Resume Next
    Err.Clear
    '   "ChuČn bŢ" cho Excel
    Set ExcelApp = GetObject(, "Excel.Application")     '   <---- dßng lÖnh nµy "că vĘn ®Ň" : nŐu ch­a më Excel _
                                                                                                                    th× dßng nµy chąy ®Őn lÇn thř 2 Kh«ng B¸o Lçi
    If Err Then
        Err.Clear
        Set ExcelApp = CreateObject("Excel.Application")
        ExcelApp.Workbooks.Add
        Set ExcelObj = ExcelApp.ActiveWorkbook.ActiveSheet
        
        '   Active window Excel
        Excel.Application.Visible = True
    Else
        Set ExcelObj = ExcelApp.ActiveWorkbook.Sheets.Add
        
        '   Active window Excel
        AppActivate ExcelApp.Caption
    End If

    i = 0
    Do
        Err.Clear
        If i = 0 Then
            ExcelObj.Name = "T.Do Diem"
        Else
            ExcelObj.Name = "T.Do Diem " & i
        End If
        i = i + 1
    Loop While Err.Number <> 0
    On Error GoTo 0
    
    ExcelObj.Cells.Font.Name = "VNI-Helve"
    ExcelObj.Cells.Font.Size = 10
    ExcelObj.Cells.HorizontalAlignment = xlCenter
    ExcelObj.Cells.VerticalAlignment = xlCenter
    
    ExcelObj.Cells(1, 1).Value = "BAŰNG TOĎA ŃOÄ"
    ExcelObj.Cells(1, 1).Font.Bold = True
    ExcelObj.Cells(1, 1).Font.Size = 11
    ExcelObj.Range(ExcelObj.Cells(1, 1), ExcelObj.Cells(1, 3 * (SLTrucToaDo - 1))).HorizontalAlignment = _
                                                                                                                                                                xlCenterAcrossSelection
    
    j = 0   '   Sč thř tů hÖ trôc täa ®é
    Do
        j = j + 1
    
        '   VĎ text VŢ trÝ
        ExcelObj.Cells(2, j * 3 - 2).Value = "VŇ TRÍ"
        
        '   VĎ text X(cm)
        ExcelObj.Cells(2, j * 3 - 1).Value = "X" & HeTTD(j - 1).TenXOY & " (" & UCase(Txt_DonVi) & ")"
       
        '   VĎ text Y(cm)
        ExcelObj.Cells(2, j * 3).Value = "Y" & HeTTD(j - 1).TenXOY & " (" & UCase(Txt_DonVi) & ")"

        i = 0       '   Sč thř tů ®iÓm
        Do
            i = i + 1
        
            '   VĎ sč thř tů
            ExcelObj.Cells(2 + i, j * 3 - 2).Value = HeTTD(j - 1).TenViTri(i - 1)

            '   VĎ täa ®é X
            ExcelObj.Cells(2 + i, j * 3 - 1).Value = Str(Round(HeTTD(j - 1).ToadoY(i - 1) * TyleBV / SoChia, Sochusole))
            
            '   VĎ täa ®é Y
            ExcelObj.Cells(2 + i, j * 3).Value = Str(Round(HeTTD(j - 1).ToadoX(i - 1) * TyleBV / SoChia, Sochusole))

        Loop Until i = HeTTD(j - 1).SoDiem
        
Dim st As String, k As Byte
        st = "#,##0."
        For k = 1 To Sochusole
            st = st & "0"
        Next k
        ExcelObj.Range(ExcelObj.Cells(3, j * 3 - 1), ExcelObj.Cells(2 + i, j * 3)).NumberFormat = st
    
        With ExcelObj.Range(ExcelObj.Cells(2, j * 3 - 2), ExcelObj.Cells(2 + i, j * 3))
            .Borders(xlEdgeLeft).LineStyle = xlContinuous
            .Borders(xlEdgeLeft).Weight = xlThin
            
            .Borders(xlEdgeTop).LineStyle = xlContinuous
            .Borders(xlEdgeTop).Weight = xlThin
            
            .Borders(xlEdgeBottom).LineStyle = xlContinuous
            .Borders(xlEdgeBottom).Weight = xlThin
            
            .Borders(xlEdgeRight).LineStyle = xlContinuous
            .Borders(xlEdgeRight).Weight = xlThin
            
            .Borders(xlInsideVertical).LineStyle = xlContinuous
            .Borders(xlInsideVertical).Weight = xlThin
            
            .Borders(xlInsideHorizontal).LineStyle = xlContinuous
            .Borders(xlInsideHorizontal).Weight = xlThin
        End With
    Loop Until j = SLTrucToaDo - 1
End Sub

(defun ETOS (arg / file)
  (if (= 'STR (type arg)) (setq arg (strcat "\"" arg "\"")))
  (setq file (open "TL" "w"))
  (princ arg file)
  (close file)
  (setq file (open "TL" "r"))
  (setq arg (read-line file))
  (close file)
  (close (open "TL" "w"))
  arg
)  
;------------------------------------------------------------------
(defun fopen ( fname mode msg / fh )
  (setq fh (open fname mode))
  (defun *error* (msg)
     (princ msg)
     (princ)
  )
  (while (= fh nil)
    (progn
       (Prompt (strcat "\nFile " msg " Not Found !"))
       (setq fname (USTR 1 (strcat "\nInput " msg " Again  ") nil T)
             fh (open fname mode)
       ) 
    )
  )
  fh
)
;------------------------------------------------------------------
(defun UDIST (bit kwd msg def bpt / inp)
  (if def
    (setq msg (strcat "\n" msg "<" (rtos def) ">: ")
          bit (* 2 (fix (/ bit 2)))
    )
    (if (= " " (substr msg (strlen msg) 1)) 
      (setq msg (strcat "\n" (substr msg 1 (1- (strlen msg))) ": "))
      (setq msg (strcat "\n" msg ": "))
    )
  )
  (initget bit kwd)
  (setq inp
    (if bpt
      (getdist msg bpt)
      (getdist msg)
    )
  )
  (if inp inp def)
)	
;------------------------------------------------------------------
(defun UKWORD (bit kwd msg def / inp)
  (if (and def (/= def ""))
    (setq msg (strcat "\n" msg "<" def ">: ")
          bit (* 2 (fix (/ bit 2)))
    )
    (if (= " " (substr msg (strlen msg) 1))
      (setq msg (strcat "\n" (substr msg 1 (1- (strlen msg))) ": "))
      (setq msg (strcat "\n" msg ": "))
    )
  )
  (initget bit kwd)
  (setq inp (getkword msg))
  (if inp inp def)
)
;------------------------------------------------------------------
(defun USTR (bit msg def spflag / inp nval)
  (if (and def (/= def ""))
    (setq msg (strcat "\n" msg "<" def ">: ")
          inp (getstring spflag msg)
          inp (if (= inp "") def inp)
    )
    (progn
      (if (= " " (substr msg (strlen msg) 1))
        (setq msg (strcat "\n" (substr msg 1 (1- (strlen msg))) ": "))
        (setq msg (strcat "\n" msg ": "))
      )
      (if (= bit 1)
        (while (= "" (setq inp (getstring spflag msg)))
           (prompt "\nInvalid String.")
        )
        (setq inp (getstring spflag msg))
      )
    )
  )
  inp
)
;------------------------------------------------------------------
(defun UINT (bit kwd msg def / inp)
  (if def
    (setq msg (strcat "\n" msg "<" (itoa def) ">: ")
	  bit (* 2 (fix (/ bit 2)))
    )
    (if (= " " (substr msg (strlen msg) 1)) 
      (setq msg (strcat "\n" (substr msg 1 (1- (strlen msg))) ": "))
      (setq msg (strcat "\n" msg ": "))
    )
  )
  (initget bit kwd)
  (setq inp (getint msg))
  (if inp inp def)
)	
;------------------------------------------------------------------
(defun UREAL (bit kwd msg def / inp)
  (if def
    (setq msg (strcat "\n" msg "<" (rtos def 2) ">: ")
	  bit (* 2 (fix (/ bit 2)))
    )
    (if (= " " (substr msg (strlen msg) 1)) 
      (setq msg (strcat "\n" (substr msg 1 (1- (strlen msg))) ": "))
      (setq msg (strcat "\n" msg ": "))
    )
  )
  (initget bit kwd)
  (setq inp (getreal msg))
  (if inp inp def)
)	
;------------------------------------------------------------------
(defun UPOINT (bit kwd msg def bpt / inp)
  (if def
    (setq pts (strcat 
                 (rtos (car def)) "," (rtos (cadr def))
                 (if
                   (and (caddr def) (= 0 (getvar "FLATLAND")))
                   (strcat "," (rtos (caddr def))) 
                   ""
                 )
               )
          msg (strcat "\n" msg "<" pts ">: ")
          bit (* 2 (fix (/ bit 2)))
    ) 
    (if (= " " (substr msg (strlen msg) 1))
       (setq msg (strcat "\n" (substr msg 1 (1- (strlen msg))) ": "))
       (setq msg (strcat "\n" msg ": "))
    )
  )
  (initget bit kwd)
  (setq inp
    (if bpt
      (getpoint msg bpt)
      (getpoint msg)
    )
  )
  (if inp inp def)
) 
;------------------------------------------------------------------
(defun CMDECH (mode)
  (if (= mode 1)
    (setvar "CMDECHO" 0)
    (setvar "CMDECHO" 1) 
  )
  (graphscr)
  (princ)
)
;------------------------------------------------------------------
(defun DXF (code elist)
  (cdr (assoc code elist))
)
;------------------------------------------------------------------
(defun RAD (degree)
  (setq radian (/ (* degree 3.1416) 180))
  radian
)
;------------------------------------------------------------------
(defun DEG (Rad)
  (setq degree (/ (* rad 180) 3.1416))
  degree
)
;------------------------------------------------------------------
(defun OSMODE ( mode )
  ( if (= mode 1) 
       (setvar "OSMODE" #OSMODE) 
       (progn
          (setq #OSMODE (getvar "OSMODE"))
          (setvar "OSMODE" 0)
       )
  )
)
;------------------------------------------------------------------
(defun c:CUT( / pt1 pt2 pt3 pt4 pt5 pt6 x1 x2 y1 y2 dx dy xx1 yy1 
                xx2 yy2 xx3 yy3 xx4 yy4 a b)
  (prompt "\nExpansion symbol. ") 
  (OSMODE 0)
  (CMDECH 1)
  (if #dist #dist (setq #dist 0))
  (setq pt1 (getpoint "\nFirst point : ")
  	pt2 (getpoint "\nSecond point : " pt1)
  	#dist (abs (UDIST 0 "" "How big (Bu co nao) ?" #dist nil))
  	x1 (car pt1)
        y1 (cadr pt1)
	x2 (car pt2)
	y2 (cadr pt2)
        a (angle pt1 pt2)
        b (- (/ PI 2) a)
	dx (* (/ #dist 3) (cos a))
	dy (if (= (cos a) 0) (/ #dist 3) (* dx (/ (sin a) (cos a))))
        xx1 (- (/ (+ x2 x1) 2) (/ dx 2))
	yy1 (- (/ (+ y2 y1) 2) (/ dy 2))
	xx2 (+ (/ (+ x2 x1) 2) (/ dx 2))
	yy2 (+ (/ (+ y2 y1) 2) (/ dy 2))
	dx  (* (/ #dist 2) (cos b))
	dy  (* (/ #dist 2) (sin b))
	xx3 (- (/ (+ x2 x1) 2) dx)
	yy3 (+ (/ (+ y2 y1) 2) dy)
	xx4 (+ (/ (+ x2 x1) 2) dx)
	yy4 (- (/ (+ y2 y1) 2) dy)
	pt3 (list xx1 yy1)
	pt4 (list xx3 yy3)
	pt5 (list xx4 yy4)
	pt6 (list xx2 yy2)
  )
(OSMODE 0)
(command "PLINE" pt1 pt3 pt4 pt5 pt6 pt2 "")
(OSMODE 1)
) 
(prompt "\n CUT() : Draw expansion symbol")
;------------------------------------------------------------------
(defun c:st( / a pt1 pt2 pt3 pt4 x1 y1 times dist dl dx dy pt)
(prompt "\nBar sections, Welding line. ")
(cmdech 1)
(if #dia dia (setq #dia 20))
(if #inter #inter (setq #inter 200))
(if #kind #kind (setq #kind "Bar"))
(setq #kind (ukword 1 "Bar Siteweld Factoryweld" " Bar, weld in Site, weld in Factory " #kind)
      pt1 (getpoint "\nFrom...")
      pt2 (getpoint "\nTo..." pt1)
      #dia (abs (UDIST 0 "" "How big :" #dia nil))
      #inter (abs (UDIST 0 "" "Interval :" #inter nil))
      x1 (car pt1)
      y1 (cadr pt1)
      a (angle pt1 pt2)
      dist (distance pt1 pt2)
      times (fix (/ dist #inter))
      dl (/ dist times)
      dx (* dl (cos a))
      dy (* dl (sin a))
)
(setq #OSMODE (getvar "OSMODE"))
(setvar "OSMODE" 0)
(while (>= times 0)
  (setq x (+ x1 (* times dx))
      y (+ y1 (* times dy))
      pt (list x y))
  (if (= #kind "Bar")
     (command "DONUT" 0 #dia pt ""))
  (if (= #kind "Factoryweld")
     (command "LINE" pt (polar pt (+ a (/ PI 2)) #dia) ""))
  (if (= #kind "Siteweld")
     (progn
        (setq pt1 (polar pt (+ a PI) (/ #dia 2))
              pt2 (polar pt a (/ #dia 2))
              pt3 (polar pt1 (+ a (/ PI 4)) (* 1.414 #dia))
              pt4 (polar pt2 (+ a (/ (* 3 PI) 4)) (* 1.414 #dia))
        )      
        (command "LINE" pt1 pt3 "")
        (command "LINE" pt2 pt4 "")
     )
  )
  (setq times (1- times))
)
(setvar "OSMODE" #OSMODE)
)
(prompt "\n ST() : Bar sections")
;------------------------------------------------------------------
(defun c:st1( / a count pt1 pt2 x1 y1 dist dl dx dy pt)
(prompt "\nBar sections. ")
(cmdech 1)
(if #dia dia (setq #dia 20))
(if #times #Hmany (setq #times 2))
(setq pt1 (getpoint "\nFrom...")
      pt2 (getpoint "\nTo..." pt1)
      #dia (abs (UDIST 0 "" "Diameter of bar :" #dia nil))
      #times (UINT 4 "" "How many bars :" #times)
      x1 (car pt1)
      y1 (cadr pt1)
      a (angle pt1 pt2)
      dist (distance pt1 pt2)
      dl (/ dist (- #times 1))
      dx (* dl (cos a))
      dy (* dl (sin a))
      count (- #times 1)
)
(setq #OSMODE (getvar "OSMODE"))
(setvar "OSMODE" 0)
(while (>= count 0)
  (setq x (+ x1 (* count dx))
      y (+ y1 (* count dy))
      pt (list x y)
  )
  (command "DONUT" 0 #dia pt "")
  (setq count (- count 1))
)
(setvar "OSMODE" #OSMODE)
)
(prompt "\n ST1() : Bar sections ")
;------------------------------------------------------------------
(DEFUN C:CW( / ss1 emax count et ed en)
  (PROMPT "\nCHANGE WIDTH ! ")
  (PROMPT " \nSelect all Entities wanted to change... ")
  (IF #width #width (setq #width 0.5))
  (cmdech 1)
  (SETQ ss1 (ssget)
      emax (sslength ss1)
      count 0
      #width (UREAL 4 "" "Enter new width for all entities " #width)
  )
  (WHILE (< count emax)
    (setq en (ssname ss1 count)
        ed (entget en)
        et (cdr (assoc 0 ed))
    )
    (if (= et "LINE") (COMMAND "PEDIT" en "Y" "W" #width ""))
    (if (= et "PLINE") (COMMAND "PEDIT" en "W" #width ""))
    (setq count (1+ count))
  )
  (princ)
)
(prompt "\n CW() : Change the width of selected entities")
;------------------------------------------------------------------
(DEFUN C:HK( / pt1 pt2 pt3 pt4 da ang1 ang2 sidepoint)
  (PROMPT "\nDraw a hook. ")
  (cmdech 1)
  (if #diaa #diaa (setq #diaa 25))
  (setq pt1 (getpoint "\nBegin from :")
        pt2 (getpoint "\nDirection..." pt1)
        sidepoint (getpoint "\nSelect side ..." pt1)
        #diaa (abs (UDIST 0 "" "Enter diameter of hook :" #diaa pt1))
        ang1 (angle pt1 pt2)
        da (angle pt1 sidepoint) 
  )
  (setq #OSMODE (getvar "OSMODE"))
  (setvar "OSMODE" 0)
  (if (and (<= ang1 4.71239) (>= ang1 1.5708))
        (if (> da ang1)
           (setq ang2 (+ ang1 (/ PI 2)))
           (setq ang2 (- ang1 (/ PI 2)))
        )
  )
  (if (and (<= ang1 1.5708) (>= ang1 0))
         (if (or (> da 4.71239) (< da ang1))
             (setq ang2 (- ang1 (/ PI 2)))
             (setq ang2 (+ ang1 (/ PI 2)))
         )
   )
   (if (and (<= ang1 6.2832) (>= ang1 4.71239))
         (if (or (<= da 1.5708) (>= da ang1))
            (setq ang2 (+ ang1 (/ PI 2)))
            (setq ang2 (- ang1 (/ PI 2)))
         ) 
   )
  (setq pt3 (polar pt1 ang2 #diaa)
        pt4 (polar pt3 (+ ang1 PI) (* 1.5 #diaa))
  )
  (command "PLINE" pt1 "A" "D" pt2 pt3 "L" pt4 "")
  (setvar "OSMODE" #OSMODE)
) 
(prompt "\n HK() : Draw a hook ")
;------------------------------------------------------------------
(defun c:HOR()
  (prompt "\nNew dim method. ")
  (setq #DIM 1)
  (setq pt1 (getpoint "\nSelect first extension line origin : ")
        pt2 (getpoint "\nSelect second extension line origin : " pt1) 
        #pt3 (getpoint "\nExtension line origin location :")
        pt11 (list (car pt1) (cadr #pt3))
        pt22 (list (car pt2) (cadr #pt3))
  )
  (command "DIM1" "HOR" pt11 pt22)
)
(prompt "\n HOR or HO to use new horizontal dim method")
;------------------------------------------------------------------
(defun c:VER()
  (prompt "\nNew dim method. ")
  (setq #DIM 2)
  (setq pt1 (getpoint "\nSelect first extension line origin : ")
        pt2 (getpoint "\nSelect second extension line origin : " pt1) 
        #pt3 (getpoint "\nExtension line origin location :")
        pt11 (list (car #pt3) (cadr pt1))
        pt22 (list (car #pt3) (cadr pt2))
  )
  (command "DIM1" "VER" pt11 pt22)
)
(prompt "\n VER or VE to use new vertical dim method")
(defun c:VE () (c:VER))
(defun c:HO () (c:HOR))
;------------------------------------------------------------------
(defun c:ALI( / pt1 pt2 pt3 pt4 pt5 pt11 dis )
   (prompt "\nNew dim method.")
   (setq #DIM 3)
   (setq pt1 (getpoint "\nSelect first extension line origin : ")
         pt2 (getpoint "\nSelect first extension line origin : " pt1)
         pt3 (getpoint "\nExtension line origin location : ")
         #A (angle pt1 pt2)
         pt4 (polar pt3 (+ #A 1.57076) 100)
         pt5 (inters pt1 pt2 pt3 pt4 seg)
         dis (distance pt3 pt5)
         pt11 (polar pt1 (+ #A 1.57076) dis)  
         #pt22 (polar pt2 (+ #A 1.57076) dis)  
   )
   (command "dim1" "ali" pt11 #pt22)
) 
(prompt "\n ALI to use new ALI dim method")
;------------------------------------------------------------------
(defun c:con( / pt1 pt11 pt4 pt5 A dis pt11 pt22)
 (if (= #DIM 1)
   (progn
      (prompt "\nNew dim method.")
      (setq pt1 (getpoint "\nSelect next extension line origin : ")
            pt11 (list (car pt1) (cadr #pt3))
      )
      (command "DIM1" "CON" pt11)
   )
 )
 (if (= #DIM 2)
   (progn
     (prompt "\nNew dim method. ")
     (setq pt1 (getpoint "\nSelect next extension line origin : ")
           pt11 (list (car #pt3) (cadr pt1))
     )
     (command "DIM1" "CON" pt11)
   )
 )
 (if (= #DIM 3)
   (progn
     (prompt "\nNew dim method. ")
     (setq pt1 (getpoint "\nSelect next extension line origin : ")
           pt2 (polar #pt22 #A 100)
           pt3 (polar pt1 (+ #A 1.570796) 100)
           pt5 (inters #pt22 pt2 pt1 pt3 seg)
     )
     (command "dim1" "con" pt5)
   )
 )
)
(prompt "\n CON to use new continuos dim method")
;------------------------------------------------------------------
(defun NS (x1 y1 x2 y2 x)
  (+ y1 (* (- x x1) (/ (float (- y1 y2)) (float (- x1 x2)))))
)
;------------------------------------------------------------------
(defun c:code( / ptlist pt a b n len pt1 ptc so pt2 count ptg)
  (if (= SCALE nil) (setq SCALE (UREAL 4 "" "Scale " SCALE)))
  (setq pt (upoint 0 "" "\nPick steel position" nil nil))
  (while (/= pt nil)
     (setq ptlist (append ptlist (list pt))
           pt (upoint 0 "" "\nPick steel position" nil pt)
     )
  )
  (setq pt1 (upoint 0 "" "\nFrom..." nil (nth 0 ptlist))
        pt2 (upoint 0 "" "\nTo..." nil pt1)
        len (distance (nth 0 ptlist) pt1)
        a (angle (nth 0 ptlist) pt1)
        b (angle pt1 pt2)
        n (length ptlist)
        ptc (polar pt2 b (* SCALE 1.6))
        count 0
  )
  (setq #OSMODE (getvar "OSMODE"))
  (setvar "OSMODE" 0)
  (while (< count n)
     (progn
        (setq pt (polar (nth count ptlist) a len)
              ptg (inters pt1 pt2 (nth count ptlist) pt seg)
        )  
        (command "LINE" (nth count ptlist) ptg "")
        (setq count (+ 1 count))
     )
  )
  (command "LINE" pt1 pt2 "")
  (if #dk #dk (setq #dk "00"))
  (setq str (strcat (rtos n 2 0) "%%c" (ustr 0 "Diameter " #dk T) " "))
  (setq so (ustr 0 "Number " "00" T))
  (if (>= (car pt2) (car pt1))
    (progn
     (command "TEXT" "J" "BR" pt2 (DEG b) str)
     (command "TEXT" "J" "MC" ptc (DEG b) so)
    )
    (progn 
     (command "TEXT" "J" "BL" pt2 (DEG (angle pt2 pt1)) str)
     (command "TEXT" "J" "MC" ptc (DEG (angle pt2 pt1)) so)
    )
  )
  (command "CIRCLE" ptc "D" (* 6 SCALE))
  (setvar "OSMODE" #OSMODE)
)
(prompt "\n CODE to code steels in a section")
;------------------------------------------------------------------
(defun c:btk( / fn fh ncol kch th i y ymin x width w dcx dcxlist colw line str)
  (setq DZ (getvar "DIMZIN"))
  (setvar "DIMZIN" 0)
  (if (= scale nil) (setq scale (getreal "\nInput current scale : ")))
  (setq kch (* 5.0 scale))
  (setq fn (USTR 4 "Nhap Ten File Du Lieu " "" T)
        fh (fopen fn "r" fn)
        ps (getpoint "Diem bat dau:")
        kch (UREAL 0 "" " Khoang cach hang " kch)
        i 1
        y (cadr ps)
        x (car ps)
        width 0
  )

  (setq #OSMODE (getvar "OSMODE"))
  (setvar "OSMODE" 0)

  (setq str (read-line fh))
  (setq ncol (length (read (strcat "(" str ")"))))
  (setq w (* 20 scale))
  (setq dcx 0)
  (while (<= i ncol)
     (progn
        (setq chuoi (strcat "Be Rong Cot Thu " (rtos i 2 0) " ")
              w (UREAL 0 "" chuoi w)
              colw (append colw (list w))
              width (+ width w)
              chuoi (strcat "Do Chinh Xac Cua Cot Thu " (rtos i 2 0) " ")
              dcx (UINT 0 "" chuoi dcx)
              dcxlist (append dcxlist (list dcx))
              i (+ 1 i)
        )
     )
  )
  (while (/= str nil)
    (progn
       (setq line (read (strcat "(" str ")")))
       (setq i 0)
       (setq y (- y kch))
       (setq x (car ps))
       (while (< i ncol) 
         (progn
            (setq So (nth i line)
                  x (+ x (/ (nth i colw) 2.0))
                  pt (list x y)
                  x (+ x (/ (nth i colw) 2.0))
            )
            (if (/= (etos So) "O")
                (if (= (type So) 'SYM)
                   (command "TEXT" "J" "MC" pt "0" (etos So))
                   (command "TEXT" "J" "MC" pt "0" (rtos (float So) 2 (nth i dcxlist)))
                )
            )
            (setq i (+ i 1))
         )
       )
       (command "LINE" (list (car ps) (+ y (/ kch 2.0))) (list (+ (car ps) width) (+ y (/ kch 2.0))) "")
       (setq str (read-line fh))
    )
  )
  (setq y (- y (/ kch 2.0)))
  (setq ymin (- (cadr ps) (/ kch 2.0)))
  (command "LINE" (list (car ps) ymin) (list (car ps) y) (list (+ (car ps) width) y) "")
  (setq i 0
        x (car ps)
  )
  (while (< i ncol)
    (progn
       (setq x (+ x (nth i colw))
             i (+ i 1)
       )
       (command "LINE" (list x ymin) (list x y) "")
    )
  )
  (close fh)
  (setvar "DIMZIN" DZ)

  (setvar "OSMODE" #OSMODE)
)
(prompt " \n BTK : Import from text file to table")
(princ)

(setvar "cmdecho" 0)
(defun DXF (code elist)
  (cdr (assoc code elist))
)
;******************************************************************
;******************************************************************
(defun refine3a ( / nsset temp ed ac)
   (setq DZ (getvar "DIMZIN"))
   (setvar "DIMZIN" 0)

  (setq ssl   (sslength sset); 
        nsset (ssadd)
  )
  (print ssl)
  (princ "entities found. ")  
  (princ "\nVerifying the selected entities ** please wait. ")
  (while (> ssl 0)
    (progn
      (setq temp (ssname sset (setq ssl (1- ssl))))
      (setq ed (entget temp))
      (if (= (DXF 0 ed) "TEXT")
        (progn
          (if (/= (TYPE (READ (DXF 1 ed))) 'SYM) 
            (ssadd temp nsset)
          )
        )
      )
    )
  )
  (setq ssl (sslength nsset)
        sset nsset
  )
  (print ssl)
  (princ "text entities found. ")
  (princ "\n play " )
  (setq d (getreal "\n Input su chenh lech giua 2 so: "))
  (setq d (/ d 1))
  (setq ac (getint "\n Input accuracy: ")) 

  (while (> ssl 0)
    (progn
      (setq temp (ssname sset (setq ssl (1- ssl))))
      (setq ed (entget temp))
      (setq old (cons 1 (DXF 1 ed)))
      (setq No (atof (DXF 1 ed)))    
      (setq No (+ No d))
      (setq new (cons 1 (rtos No 2 ac)))
      (setq ed (subst new old ed))
      (entmod ed)  
    )
  )
(setvar "DIMZIN" DZ)
)
;******************************************************************
;******************************************************************
(defun refine4a ( / nsset temp ed ac)
   (setq DZ (getvar "DIMZIN"))
   (setvar "DIMZIN" 0)

  (setq ssl   (sslength sset); 
        nsset (ssadd)
  )
  (print ssl)
  (princ "entities found. ")  
  (princ "\nVerifying the selected entities ** please wait. ")
  (while (> ssl 0)
    (progn
      (setq temp (ssname sset (setq ssl (1- ssl))))
      (setq ed (entget temp))
      (if (= (DXF 0 ed) "TEXT")
        (progn
          (if (/= (TYPE (READ (DXF 1 ed))) 'SYM) 
            (ssadd temp nsset)
          )
        )
      )
    )
  )
  (setq ssl (sslength nsset)
        sset nsset
  )
  (print ssl)
  (princ "text entities found. ")
  (princ "\n play " )
  (setq d (getreal "\n Input so lan tang giam giua 2 so: "))
  (setq d (/ d 1))
  (setq ac (getint "\n Input accuracy: ")) 

  (while (> ssl 0)
    (progn
      (setq temp (ssname sset (setq ssl (1- ssl))))
      (setq ed (entget temp))
      (setq old (cons 1 (DXF 1 ed)))
      (setq No (atof (DXF 1 ed)))    
      (setq No (* No d))
      (setq new (cons 1 (rtos No 2 ac)))
      (setq ed (subst new old ed))
      (entmod ed)  
    )
  )
(setvar "DIMZIN" DZ)
)
;******************************************************************
;******************************************************************
(defun c:u1()
(setq sset (ssget))
(refine3a)
)
;******************************************************************
(defun c:u3()
(setq sset (ssget))
(refine4a)
)
;************************************************************************
(defun C:DE()
 (setvar "DIMDEC" 2) ;So thap phan
 (command "osnap" "inter")
 (prompt "\nDistance measuring method written by DUONG VAN SANG, TEDI South.")
 (prompt "\nStart command with DE (abbreviation of DISTANCE).")
 (if (= scale1 nil)
     (setq SCALE1 (getreal "\nInput current scale : ")))
 (setq _SCALE (/ 200.0 SCALE1))
 (setq TYLE (/ 200.0 _SCALE)
       tl_cm (/ TYLE 10.0)
 )
 (setq p1 (getpoint "\nSelect the first point : ")
       p2 (getpoint "\nSelect the second point: ")
       len (* tl_cm (abs (- (car p2) (car p1))))
 )
 (if (>= (car p2) (car p1))
       (setq p3 (polar p1 0 (/ len (* 2 tl_cm))))
       (setq p3 (polar p2 0 (/ len (* 2 tl_cm))))
 )
 (setq p4 (polar p3 -1.5707963268 (* 2.5 _SCALE)))
 (command "osnap" "none")
 (if (>= (/ len 100) 1)
     (command "text" "s" "standard" "M" p4 (* 2.0 _SCALE) 0 (rtos (/ (* 1 len) 100) 2 2) )
     (command "text" "s" "standard" "M" p4 (* 2.0 _SCALE) 90 (rtos (/ (* 1 len) 100) 2 2) )
 )
 (setvar "DIMDEC" 1) ;So thap phan
 (princ)
)
;************************************************************************
(defun C:HT()
 (setvar "DIMDEC" 2) ;So thap phan
 (prompt "\nHeight measuring method written by DUONG VAN SANG, TEDI South.")
 (prompt "\nStart command with HT (abbreviation of HEIGHT).")
 (if (= scale1 nil)
     (setq SCALE1 (getreal "\nInput current scale : ")))
 (setq _SCALE (/ 200.0 SCALE1))
 (setq TYLE (/ 200.0 _SCALE)
       tl_cm (/ TYLE 10.0)
 )
 (setq p1 (getpoint "\nChon diem lam goc toa do     : ")
       y  (getreal  "\nToa do y cua goc toa do (m)  : "))

 (setq  Loop 1)   
 (While 
   (<= Loop 32767)
   (progn
    
    (setq  p2 (getpoint "\nChon diem can xac dinh cao do: ")
           p3 (getpoint "\nChon diem ghi dong text      : ")
           p4 (polar p3 -1.5707963268 (* 6.0 _SCALE))
          len (* tl_cm (- (cadr p2) (cadr p1)))
   )
   (command "text" "s" "standard" "M" p4 (* 2.0 _SCALE) 90 (rtos (+ y (/ len 100)) 2 2) )

   )
   ( setq Loop (1+ Loop))
 );end of while
 (setvar "DIMDEC" 1) ;So thap phan
 (princ)
)
;************************************************************************
(defun C:FF()
 (command "osnap" "inter")
 (prompt "\nAutoCAD Utilities written by DUONG VAN SANG, TEDI South.")
 (prompt "\nStart command with FF. ")
 (if (= scale1 nil)
     (setq SCALE1 (getreal "\nInput current scale : ")))
 (setq _SCALE (/ 200.0 SCALE1))
 (setq TYLE (/ 200.0 _SCALE)
       tl_cm (/ TYLE 10.0)
       KHCACH (/ 65.0 tl_cm)
 )
 (setq d1 (getpoint "\nSelect the first point : ")
       d2 (getpoint "\nSelect the second point: ")
       len (abs (- (car d2) (car d1)))
 )
 (setq d3 (polar d1 -1.5707963268 KHCACH))
 (if (>= (NTH 0 d2) (NTH 0 d1))
     (setq d4 (polar d3 0 len))
     (setq d4 (polar d3 PI len))
 )
 (command "osnap" "none")
 (command "LINE" d1 d3 d4 d2 "")
 (princ)
)
;************************************************************************
(defun C:MM()
 (command "osnap" "inter")
 (prompt "\nAutoCAD Utilities written by DUONG VAN SANG, TEDI South.")
 (prompt "\nStart command with MM. ")
 (if (= scale1 nil)
     (setq SCALE1 (getreal "\nInput current scale : ")))
 (setq _SCALE (/ 200.0 SCALE1))
 (setq TYLE (/ 200.0 _SCALE)
       tl_cm (/ TYLE 10.0)
       KHCACH (/ 65.0 tl_cm)
 )
 (setq d1 (getpoint "\nSelect the first point : ")
       d2 (getpoint "\nSelect the second point: ")
       len (/ 100.0 tl_cm)
 )
 (setq d3 (polar d1 -1.5707963268 KHCACH))
 (if (>= (NTH 0 d2) (NTH 0 d1))
     (setq d4 (polar d3 0 len))
     (setq d4 (polar d3 PI len))
 )
 (setq d2 (list (nth 0 d4) (nth 1 d2)))
 (command "osnap" "none")
 (command "LINE" d1 d3 d4 d2 "")
 (princ)
)
;************************************************************************
(defun C:RR()
 (command "osnap" "NEAR")
 (prompt "\nAutoCAD Utilities written by DUONG VAN SANG, TEDI South.")
 (prompt "\nStart command with RR. ")
 (if (= scale1 nil)
     (setq SCALE1 (getreal "\nInput current scale : ")))
 (setq _SCALE (/ 100.0 SCALE1))
 (setq d1 (getpoint "\nSelect the first point : ")
       d2 (getpoint "\nSelect the second point: ")
       len (abs (- (car d2) (car d1)))
       d3  (polar d2 -1.5707963268 (* _SCALE 3.75))
 )
 (if (>= (NTH 0 d2) (NTH 0 d1))
   (progn
     (setq d4  (polar d3 2.967 (* _SCALE 2.0))
           d5  (polar d3 3.316 (* _SCALE 2.0))
     )
   )
   (progn
     (setq d4  (polar d3 0.1745 (* _SCALE 2.0))
           d5  (polar d3 6.1087 (* _SCALE 2.0))
     )
   )
 )
 (command "osnap" "none")
 (command "LINE" d3 d4 "")
 (command "LINE" d3 d5 "")
 (if (>= (NTH 0 d1) (NTH 0 d2))
     (progn
       (setq d8 d1
             d1 d2
             d2 d8
       )
     )
 )
 (setq d7  (polar d1 -1.5707963268 (* _SCALE 7.5))
       d8  (polar d2 -1.5707963268 (* _SCALE 7.5))
 )
 (command "LINE" d1 d7 "")
 (command "LINE" d2 d8 "")
 (setq d3  (polar d1 -1.5707963268 (* _SCALE 3.75))
       d4  (polar d3 0 (- (/ len 2) (* _SCALE 4.5)))
       d5  (polar d4 -0.785398 (* _SCALE 4.24264))
       d8  (polar d2 -1.5707963268 (* _SCALE 3.75))
       d7  (polar d8 pi (- (/ len 2) (* _SCALE 4.5)))
       d6  (polar d7 3.92699 (* _SCALE 4.24264))
 )
 (command "LINE" d3 d4 d5 d6 d7 d8 "")
 (setq d8 (list (/ (+ (nth 0 d1) (nth 0 d2)) 2) (- (nth 1 d2) (* _SCALE 3.5))))
 (command "text" "s" "standard" "BC" d8 (* 2.0 _SCALE) 0 "L=" )
 (princ)
)
;************************************************************************
(defun c:12()
 (command "osnap" "MID")
 (setq d1 (getpoint "\nSelect the point to insert the object: "))
 (command "osnap" "none")
 (COMMAND "insert" "12L.dwg" d1 "1" "1" "0")
 (princ)
)
;******************************************************************
(defun c:21()
 (command "osnap" "MID")
 (setq d1 (getpoint "\nSelect the point to insert the object: "))
 (command "osnap" "none")
 (COMMAND "insert" "12R.dwg" d1 "1" "1" "0")
 (princ)
)
;******************************************************************
(defun c:15()
 (command "osnap" "MID")
 (setq d1 (getpoint "\nSelect the point to insert the object: "))
 (command "osnap" "none")
 (COMMAND "insert" "115L.dwg" d1 "1" "1" "0")
 (princ)
)
;******************************************************************
(defun c:51()
 (command "osnap" "MID")
 (setq d1 (getpoint "\nSelect the point to insert the object: "))
 (command "osnap" "none")
 (COMMAND "insert" "115R.dwg" d1 "1" "1" "0")
 (princ)
)
;******************************************************************
(defun c:W1()
 (command "osnap" "inter")
 (setq d1 (getpoint "\nSelect the point to insert the object: "))
 (command "osnap" "none")
 (COMMAND "insert" "ongnuoc.dwg" d1 "1" "1" "0")
 (princ)
)
;******************************************************************
(defun c:W2()
 (command "osnap" "inter")
 (setq d1 (getpoint "\nSelect the point to insert the object: "))
 (command "osnap" "none")
 (COMMAND "insert" "ongnuoc2.dwg" d1 "1" "1" "0")
 (princ)
)
;******************************************************************
(prompt "\nU1: Cong 1 so voi 1 so tang giam Delta.")
(prompt "\nU3: Nhan 1 so voi 1 so tang giam Delta.")
(prompt "\nW1: Chen dong TEXT 'ONG NUOC' cho trac ngang cau CO MAY.")
(prompt "\nDE: Do khoang cach le tren trac ngang.")
(prompt "\nHT: Do cao do tren trac ngang.")
(princ)

(defun C:SXY (/ holdosmode AA PT X Y L1 L2)
  (command "_.undo" "_be")
  (setq holdosmode (getvar "osmode"))
  (setvar "osmode" 39)
  (defun LL ()
    (setq L1 (getdist "\n Reference length"))
    (setq L2 (getdist "\n New Length"))
  )
  (while (= AA NIL)
    (setq AA (ssget))
  )
  (setq PT (getpoint "\nBase point: "))
  (setq X (getstring "\nScaleX or [Reference] <1>: "))
  (cond
    ((= X "") (setq X 1))
    ((or (= X "R") (= X "r"))
     (LL)
     (setq X (/ L1 L2))
    );het cond
    (t
     (setq X (atof X))
    )
  )
  (setq Y (getstring (strcat "\nScaleY or [Reference] <" (rtos X) ">: ")
   )
  )
  (cond
    ((= Y "") (setq Y X))
    ((or (= Y "R") (= Y "r"))
     (LL)
     (setq Y (/ L1 L2))
    )
  )
  (setq A (rtos (* (getvar "CDATE") 1E8)))
  (command "_.BLOCK" A PT AA "")
  (command "_.INSERT" A PT X Y "")
  (command "_.EXPLODE" "L")
  (prompt "\n")
  (command "_.purge" "b" A "n")
  (setvar "osmode" holdosmode)
  (command "_.undo" "_end")
  (princ)
)

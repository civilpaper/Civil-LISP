(defun c:tkt(/ currentdir tmode i ss ssl list_ssi loai ssi name basept)
  (setq tmode (getvar "TILEMODE"))
  (If (= tmode 0) (Setvar "TILEMODE" 1))
  (setq currentdir (getvar "DWGPREFIX"))
  (setq path (getfiled "Select a your project Folder" currentdir "dwg" 1))
  (setq i (- (strlen path) 1))
  (while (> i 1)
    (setq sb (substr path i 1))
    (if (= sb "\\")
      (progn
	(setq pathw (substr path 1 i))
	(setq i 1)
      )
    )
    (setq i (- i 1))
  )
  (setq pathw (strcat pathw "xref.dwg"))
  (setq ss (ssget "x"))
  (setq ssl (sslength ss))
  (setq i 0)
  (while (< i ssl)
    (progn
      (setq ssi (ssname ss i))
      (setq list_ssi (entget ssi))
      (setq loai (dxf 0 (entget ssi)))
      (if (= loai "INSERT")
	(progn
	  (setq name (dxf 2 (entget ssi)))
	  (if (= name "Mp_gocin") (setq basept (DXF 10 (entget ssi))))	  
	)
      )
    )
    (setq i (+ i 1))
  )
  (command ".export" pathw "" basept "all" "" ^c ^c)
)
;===========================================================================
(defun c:ckt(/ unit tmode )
  (setq tmode (getvar "TILEMODE"))
  (If (= tmode 1) (Setvar "TILEMODE" 0))
  (setq unit (getvar "INSUNITS"))
  (setvar "INSUNITS" 4)
  (setvar "FILEDIA" 0)
  (command ".xref" "a" "xref" (setq pt (getpoint "\nInsert point: ")) "" "" "" "")
  (command ".zoom" "e" ^c ^c)
  (setvar "FILEDIA" 1)
  (setvar "INSUNITS" unit)
)

;;;;;;;;;;;;;;;;;;;;;;;;;;;;;;;;;;;;;;;;;;;;;;;;;;

(defun ckt(mp_dc /)
  (setq tmode (getvar "TILEMODE"))
  (If (= tmode 1) (Setvar "TILEMODE" 0))
  (setq unit (getvar "INSUNITS"))
  (setvar "INSUNITS" 4)
  (setvar "FILEDIA" 0)
  (command ".xref" "a" "xref" mp_dc "" "" "" "")
  ;(command ".zoom" "e" ^c ^c)
  (setvar "FILEDIA" 1)
  (setvar "INSUNITS" unit)
)


;;;;;;;;;;;;;;;;;;;;;;;;;;;;;;

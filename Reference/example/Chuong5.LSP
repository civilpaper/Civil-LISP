; Ten file: Chuong5.lsp
(prompt "\n KR: Khoet ranh tu hai duong tron")
(prompt "\n KRO: Khoet ranh tu hai duong tron khac nhau")
;-----------------------------------------------------------------------------------
(defun C:KR ()
  (setvar "osmode" 512)
  (setq N1 (getpoint "\n Kich diem tren duong tron thu nhat: ")
	N2 (getpoint "\n Kich diem tren duong tron thu hai: ")
	)
  (setvar "osmode" 0)
  (setq C1 (osnap N1 "cen")
	C2 (osnap N2 "cen")
	)
  (setq R (distance C1 N1))
  (setq G1 (angle C1 C2)
	G2 (+ (* 0.5 pi) G1)
	)
  (setq P1 (polar C1 G2 R)
	P2 (polar P1 G1 (distance C1 C2))
	)
  (command ".line" P1 P2 ""
	   ".select" "last" "")
    (setq T1 (polar C1 G1 R)
	  T2 (polar C2 (+ pi G1) r)
	  )
  (setq M (osnap P1 "Mid"))
  (command ".offset" (* 2 r) M T1 "")
  (command ".trim" "last" "p" "" T1 T2 "")
  (princ)
  )
;-----------------------------------------------------------------------------------
(defun C:KRO ( )
  (setq ;L (getreal "\n Khoang cach giua tam duong tron: L = ")
	;G (getangle "\n Goc giua tam duong tron: G = ")
    	C1 (getpoint "\n Tam duong tron thu nhat: ")
	R1 (getreal "\n Ban kinh duong tron thu nhat: R1 = ")
	)
  (command ".circle" C1 R1 "" )
  (Setq R2 (getreal "\n Ban kinh duong tron thu hai: R2 = ")
  	C2 (getpoint "\n Tam duong tron thu hai: ")
	)
  (command ".circle" C2 R2 "")
  (setq L (distance C1 C2))
  (setvar "osmode" 512)
  (setq N1 (getpoint "\n Kich diem tren duong tron thu nhat: ")
	N2 (getpoint "\n Kich diem tren duong tron thu hai: ")
	)
  (setvar "osmode" 0)
  (Setq G1 (+ (* 0.5 pi) G))
  (setq P1 (polar C1 G1 R1)
	P2 (polar C2 G1 R2)
	)
  (command ".line" "tan" P1 "tan" P2 ""
	   ".select" "last" ""
	   )
  (command ".mirror" "p" "" "cen" N1 "cen" N2 "")
  (princ)
  )
  ;(setq R (distance C1 N1))
  ;(setq G1 (angle C1 C2)
;	G2 (+ (* 0.5 pi) G1)
;	)
;  (setq P1 (polar C1 G2 R)
;	P2 (polar P1 G1 (distance C1 C2))
;	)
;  (command ".line" P1 P2 ""
;	   ".select" "last" "")
;    (setq T1 (polar C1 G1 R)
;	  T2 (polar C2 (+ pi G1) r)
;	  )
;  (setq M (osnap P1 "Mid"))
; (command ".offset" (* 2 r) M T1 "")
;  (command ".trim" "last" "p" "" T1 T2 "")
;  (princ)
;  )

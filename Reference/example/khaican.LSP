(Defun C:R2 (/ Num Root S)
	(setvar "cmdcho" 0)
;	(Initget 1)
	(Setq Num (Getreal "\n Enter base number:"))           
	(Setq R (Getreal "\n Enter Root level: "))
	(setq S (rem R 2))
	(if (< Num 0)
	  (if (/= 0 S)			
	      (Prompt "\n The specified root is :")
	      (exp (/ (Log Num) R))
	      (prompt "\n I can't Caculate this Expression")
	   )  
	    ;(progn
	    ;(prompt "\n Because Number is a Negative Number so R must be an old number:")
	    ;(initget 1 " Yes No ")
	    ;(if ( = "Yes" (Getkword "\n Do you want to enter other Root level? < Y/N >:"))
	     ; (Setq R (Getreal "\n Enter Root level: "))
	      ;(prompt " I can't canculate for you")
	    ;)							
	 ;)							
	;(Prompt "\n The specified root is :")(exp (/ (Log N) R))		
        (Prompt "\n The specified root is :")
	(exp (/ (Log Num) R))
)
 )

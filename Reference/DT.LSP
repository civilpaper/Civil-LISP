(defun DXF (code elist)
  (cdr (assoc code elist))
);dxf

(defun c:AR(/ dtl dtcon pt1 pt2 ss et oslast vsize)
  (if (= tl nil) (progn
    (setq tl (getreal "\nDrawing scale : "))
;    (setq ntl (/ 1000 tl))
;    (setq tl2 (* ntl ntl))
    )
  )
  (setq dtl 0)
  (setq ss (ssadd))
  (setq oslast (getvar "OSMODE"))
  (command "osnap" "")
   (setq ntl (/ 1000 tl))
   (setq tl2 (* ntl ntl))

  (print)
  (print)
  (setq pt1 (getpoint "\nPick internal point : "))
  (while (/= pt1 nil)
    (command "-boundary" pt1 "")
    (setq et (entlast))
    (ssadd et ss)
    (command "area" "e" "last")
    (setq vsize ( /(getvar "VIEWSIZE") 5))
    (command "hatch" "ANSI31" vsize "0" "last" "")
    (setq et (entlast))
    (ssadd et ss)
    (setq dtcon (/ (getvar "AREA") tl2))
    (setq dtl (+ dtcon dtl))
    (prompt (strcat "\nComponent area : " (rtos dtcon 2 4)))
    (print)
    (print)
    (setq pt1 (getpoint "\nPick internal point : "))
  )
  (command "setvar" "OSMODE" oslast)
  (command "erase" ss "")
  (setq ss nil)
  (command "redraw")
;  (setq dtl (/ (/ dtl tl2) 2)) 
;  (setq dtl (/ dtl 2)) 
  (print)
  (prompt (strcat "\nTotal area : " (rtos dtl 2 4)))
  (print)
  (setq pt2 (getpoint "\nPoint to write: "))
  (if (/= 0 (DXF 40 (tblsearch "STYLE" (getvar "TEXTSTYLE"))))
    (command "text" pt2  "0" (rtos dtl 2 2))
    (command "text" pt2 "2" "0" (rtos dtl 2 2))
  );if
  (princ)
);defun AR
;------------------------------------------------------------------------
(defun c:AR2(/ dtl dtcon pt1 pt2 ss et oslast vsize)
  (if (= tl nil) (progn
    (setq tl (getreal "\nDrawing scale : "))
;    (setq ntl (/ 1000 tl))
;    (setq tl2 (* ntl ntl))
    )
  )
  (setq dtl 0)
  (setq ss (ssadd))
  (setq oslast (getvar "OSMODE"))
  (command "osnap" "")
   (setq ntl (/ 1000 tl))
   (setq tl2 (* ntl ntl))

  (print)
  (print)
  (setq pt1 (getpoint "\nPick internal point : "))
  (while (/= pt1 nil)
    (command "-boundary" pt1 "")
    (setq et (entlast))
    (ssadd et ss)
    (command "area" "e" "last")
    (setq vsize ( /(getvar "VIEWSIZE") 5))
    (command "hatch" "ANSI31" vsize "0" "last" "")
    (setq et (entlast))
    (ssadd et ss)
    (setq dtcon (/ (getvar "AREA") tl2))
    (setq dtl (+ dtcon dtl))
    (prompt (strcat "\nComponent area : " (rtos dtcon 2 4)))
    (print)
    (print)
    (setq pt1 (getpoint "\nPick internal point : "))
  )
  (command "setvar" "OSMODE" oslast)
  (command "erase" ss "")
  (setq ss nil)
  (command "redraw")
;  (setq dtl (/ (/ dtl tl2) 2)) 
  (setq dtl (/ dtl 2)) 
  (print)
  (prompt (strcat "\nHaft total area : " (rtos dtl 2 4)))
  (print)
  (setq pt2 (getpoint "\nPoint to write: "))
  (if (/= 0 (DXF 40 (tblsearch "STYLE" (getvar "TEXTSTYLE"))))
    (command "text" pt2  "0" (rtos dtl 2 2))
    (command "text" pt2 "2" "0" (rtos dtl 2 2))
  );if
  (princ)
);defun AR2
;-------------------------------------------------------------------------------
(defun C:vd()
  (print)
  (print)
  (print)
 (setq last (getvar "OSMODE"))
 (command "setvar" "OSMODE" "33")
 (command "setvar" "DIMZIN" 0 )

  (if (= tl nil) (setq tl (getreal "Ty le ban ve : ")))

  (setq PT1 (getpoint "Diem 1 : "))
;  (setq PT2 (getpoint "Diem 2 : "))
;  (setq dist1 (distance pt1 pt2))
;  (setq ntl (/ 1000 tl))
;  (setq dist (/ dist1 ntl))
   (setq sum 0)

(while (/= pt1 nil)
    (setq PT2 (getpoint "Diem 2 : "))
    (print)
    (setq dist1 (distance pt1 pt2))
    (setq ntl (/ 1000 tl))
    (setq dist (/ dist1 ntl))
    (prompt (strcat "\n Chieu dai doan vua do la " (rtos dist 2 4)))
    (print)
    (setq sum (+ sum dist))
    (setq PT1 (getpoint "Diem 1 : "))
);while

(prompt (strcat "\n Tong chieu dai la " (rtos sum 2 4)))
(print)
(command "setvar" "OSMODE" "64")
(setq pt3 (getpoint "Viet vao cho nao ? : "))
;(setq x (+ (car pt3) 2))
;(setq pt3 (list x (cadr pt3)))
(setq sum2 (/ sum 2))

  (command "text" "S" "2" pt3 "0" (rtos sum2 2 2))

(command "setvar" "OSMODE" last)
(princ)
)

(prompt "\n Start with AR to calculate area by pick points method")
(prompt "\n Start with AR2 to calculate haft area by pick points method")
(prompt "\n Danh VD de tinh tong chieu dai ")
(prompt "\n This version is used for NGUYEN TRI PHUONG only - 3/10/1999")
(princ)

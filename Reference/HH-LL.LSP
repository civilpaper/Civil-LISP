(vmon)
;*
;*
(defun C:hH ()
(if (= tl nil) (setq tl (getreal "Ty le ban ve : ")))  
(setq my tl)
  (setq sy (/ 1000.0 my))
  (command "layer" "s" 0 "")
  (SETQ LAST (GETVAR "OSMODE"))
  (command "osnap" "NONE")
  (print)
  (print)
  (print)
  (command "osnap" "NEAREST")
  (setq pt (osnap (getpoint "Diem goc toa do <nearest to> : ") "nearest"))
  (print)
  (setq yo (cadr pt))
  (setq pt (osnap (getpoint "Noi ghi cao do <nearest to>  : ") "nearest"))
  (print)
  (setq y2 (cadr pt))
  (setq y1 (- y2 (* 1 sy)))
  (setq y3 (+ y2 (* 2 sy)))
  (command "osnap" "")
  (command "osnap" "END")
  (setq pt (osnap (getpoint "Diem chuan < end of )        : ") "end"))
  (print)
  (setq yc (cadr pt))
  (initget (+ 1 4))
  (setq hc (getreal "Cao do : "))
  (setq dy (- (* sy hc) yc))
  (setq kk " ")
  (while (= kk " ")
    (print)
    (print)
    (print)
    (command "osnap" "END")
    (setq pt (osnap (getpoint " Diem < end of > : ") "end"))
    (command "osnap" "")
    (setq x (car pt) y (cadr pt))
    (setq h (/ (+ y dy) sy))
    (setq x1 (+ x (* 0.1 sy)))
    (command "line" (list x y1) (list x y2) "")
    (command "layer" "s" 3 "")
    (command "line" (list x yo) (list x y) "")
    (command "layer" "s" 0 "")
    (command "text" "r" (list x1 y3) (* 0.4 sy) 90 (rtos h 2 2))
    (command "osnap" "END")
  )
    (SETVAR "OSMODE" LAST)
)
;*
;*
(defun C:LL ()
  (if (= tl nil) (setq tl (getreal "Ty le ban ve : ")))  
  (setq mx tl)
    (setq sx (/ 1000.0 mx))
  (setq lmin4 (/ 1.0 sx))
  (setq lmin3 (/ 0.8 sx))
  (setq lmin1 (/ 0.3 sx))
  (command "layer" "s" 0 "")
  (SETQ LAST (GETVAR "OSMODE"))
  (command "osnap" "NONE")
  (print)
  (print)
  (print)
  (command "osnap" "nearest")
  (setq pt (osnap (getpoint "Noi ghi cu ly <nearest to> : ") "nearest"))
  (command "osnap" "")
  (setq y1 (cadr pt))
  (setq y2 (+ y1 (* 1.0 sx)))
  (setq yc (+ y1 (* 0.5 sx)))
  (setq yc1 (+ y1 (* 0.2 sx)))
  (setq yc2 (+ y1 (* 0.8 sx)))
  (setq kkk " ")
  (while (= kkk " ")
    (print)
    (print)
    (print)
    (command "osnap" "end")
    (setq pt (osnap (getpoint "Diem 1 < end of > : ") "end"))
    (setq x1 (car pt))
    (print)
    (setq pt (osnap (getpoint "Diem 2 < end of > : ") "end"))
    (setq x2 (car pt))
    (command "osnap" "")
    (if (< x2 x1) (progn
      (setq xg x2)
      (setq x2 x1)
      (setq x1 xg)
      )
    )
    (setq dx (- x2 x1))
    (setq xt (/ dx sx))
    (setq sxt (rtos xt 2 2))
    (if (> xt 0.1) (progn
      (setq kt " ")
      (while (= kt " ")
        (setq kk (substr sxt 1 1))
        (if (= kk " ") (setq sxt (substr sxt 2)))
        (setq kt kk)
      )
      (setq len (strlen sxt))
      (setq kt (substr sxt len 1))
      (while (= kt "0")
        (setq len (- len 1))
        (setq sxt (substr sxt 1 len))
        (setq kt (substr sxt len 1))
      )
      (if (= kt ".") (progn
        (setq len (- len 1))
        (setq sxt (substr sxt 1 len))
        )
      )
      (setq len (strlen sxt))
      (setq xg (/ (+ x1 x2) 2.0))
      (setq xg1 (+ xg (* 0.1 sx)))
      (setq x1 (+ x1 (* 0.1 sx)))
      (setq x2 (- x2 (* 0.1 sx)))
      (setq len1 -1)
      (if (> len 3) (setq len1 1))
      (if (= len 2) (setq len1 1))
      (if (> len1 0) (progn
        (if (< xt lmin4) (command "text" "m" (list xg yc) (* 0.4 sx) 90 sxt) (command "text" "m" (list xg yc) (* 0.4 sx) 0 sxt))
        )
      )
      (if (= len 3) (progn
        (if (< xt lmin3) (command "text" "f" (list xg1 yc1) (list xg1 yc2) (* 0.4 sx) sxt) (command "text" "m" (list xg yc) (* 0.4 sx) 0 sxt))
        )
      )
      (if (= len 1) (progn
        (if (< xt lmin1) (command "text" "f" (list xg1 yc1) (list xg1 yc2) (* 0.4 sx) sxt) (command "text" "m" (list xg yc) (* 0.4 sx) 0 sxt))
        )
      )
      )
    )
  )
    (SETVAR "OSMODE" LAST)
)
(defun C:X()
  (command "osnap" "end,int")
)
;*
;*
(defun C:LT ()
(if (= tl nil) (setq tl (getreal "Ty le ban ve : ")))  
(setq mx tl)
  (setq sx (/ 1000.0 mx))
  (command "layer" "s" 0 "")
  (SETQ LAST (GETVAR "OSMODE"))
  (command "osnap" "NONE")
  (print)
  (print)
  (print)
  (command "osnap" "NEAREST")
  (setq pt (osnap (getpoint "Noi ghi ly trinh <nearest to>  : ") "nearest"))
  (print)
  (setq x1 (car pt))
  (setq y2 (cadr pt))
  (setq y1 (- y2 (* 1 sx)))
  (command "osnap" "")
  (command "osnap" "END")
  (setq pt (osnap (getpoint "Diem chuan < end of )        : ") "end"))
  (print)
  (setq xc (car pt))
  (initget (+ 1 4))
  (setq Lc (getreal "Ly trinh: "))
  (setq dx (- (* sx Lc) xc))
  (setq kk " ")
  (while (= kk " ")
    (print)
    (print)
    (print)
    (command "osnap" "END")
    (setq pt (osnap (getpoint " Diem < end of > : ") "end"))
    (command "osnap" "")
    (setq x (car pt) y (cadr pt))
    (setq L (/ (+ x dx) sx))
    (command "layer" "s" 0 "")
    (command "text" "r" (list x y1) (* 0.4 sx) 90 (rtos L 2 2))
    (command "osnap" "END")
  )
    (SETVAR "OSMODE" LAST)
)
;*

(defun C:VIET ()
  (command "layer" "s" 0 "")
  (setq pt (getpoint "Diem chuan : "))
  (setq xc (car pt) yc (cadr pt))
  (initget (+ 1 4))
  (print)
  (setq b1 (getreal "Vet bun : "))
  (initget (+ 1 4))
  (setq b2 (getreal "Dap cat : "))
;  (initget (+ 1 4))
;  (setq b3 (getreal "Dap dat : "))
  (setq xc1 (- xc 72))
  (setq xl11 (- xc1 9) yl11 yc)
  (setq xl12 (- xc1 8) yl12 (+ yc 2))
  (setq xc11 (+ xc1 2))
  (setq xc12 (+ xc1 18))
  (setq xc13 (+ xc1 21))
  (setq xc2 (+ xc 55))
  (setq yc21 (- yc 3))
  (setq yc22 (- yc 5))
  (setq xl21 (- xc2 9) yl21 yc21)
  (setq xl22 (- xc2 8) yl22 (+ yc21 2))
  (setq xc21 (+ xc2 2))
  (setq xc22 (+ xc2 18))
  (setq xc23 (+ xc2 21))
  (command "layer" "s" 0 "")
  (command "text" "r" (list xc1 yc) 2 0 "S  2 : ")
  (command "line" (list xl11 yl11) (list xl12 yl12) "")
  (command "text" "f" (list xc11 yc) (list xc12 yc) 2 "Vet bun :")
  (command "text" "r" (list xc2 yc21) 2 0 "S  2 : ")
  (command "line" (list xl21 yl21) (list xl22 yl22) "")
  (command "text" "f" (list xc21 yc) (list xc22 yc) 2 "Dap cat :")
  (command "text" "f" (list xc21 yc22) (list xc22 yc22) 2 "Dap dat :")
  (command "text" (list xc13 yc) 2 0 (rtos b1 2 2))
  (command "text" (list xc23 yc) 2 0 (rtos b2 2 2))
;  (command "text" (list xc23 yc22) 2 0 (rtos b3 2 2))
  (command "layer" "s" 0 "")
)


(prompt "\n Start with LT to calculate chainage")
(prompt "\n Start with HH to calculate height of points")
(prompt "\n Start with LL to calculate distance between two points")
(princ)

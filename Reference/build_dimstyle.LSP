(defun build_dimstyle (/)
  (if (not (tblsearch "dimstyle" "standard"))
    (command "_.-dimstyle" "_s" "??")
    (command "_.-dimstyle" "_r" "standard")
  )
  (princ "start setting")
  (foreach item	'(("dimtxt" 3.5)
		  ("DIMADEC" 2)
		  ("DIMALTRND" 0.0000)
		  ("DIMARCSYM" 2)
		  ("DIMASZ" 2.5000)
		  ("DIMATFIT" 3)
		  ("DIMAUNIT" 0)
		  ("DIMAZIN" 0)
		 )
    (apply 'setvar item)
  )
  (command "_.-dimstyle" "_s" "standard" "_yes")
)

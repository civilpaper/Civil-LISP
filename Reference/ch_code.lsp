; Text utilities - Written by TrongLe NT & ChienThang - Sep. 15, 1998
;(prompt "\nChange Code - Written by TrongLe NT & ChienThang - Loading...")
;------------------------------------------------------------------
(defun UKWORD (bit kwd msg def / inp)
     (if (and def (/= def ""))
          (setq msg (strcat "\n" msg "<" def ">: ")
               bit (* 2 (fix (/ bit 2)))
          )
          (if (= " " (substr msg (strlen msg) 1))
               (setq msg (strcat "\n" (substr msg 1 (1- (strlen msg))) ": "))
               (setq msg (strcat "\n" msg ": "))
          )
     )
     (initget bit kwd)
     (setq inp (getkword msg))
     (if inp inp def)
)
;------------------------------------------------------------------
(defun USTR (bit msg def spflag / inp nval)
     (if (and def (/= def ""))
          (setq msg (strcat "\n" msg "<" def ">: ")
               inp (getstring spflag msg)
               inp (if (= inp "") def inp)
          )
          (progn
               (if (= " " (substr msg (strlen msg) 1))
                    (setq msg (strcat "\n" (substr msg 1 (1- (strlen msg))) ": "))
                    (setq msg (strcat "\n" msg ": "))
               )
               (if (= bit 1)
                    (while (= "" (setq inp (getstring spflag msg)))
                         (prompt "\nInvalid String.")
                    )
                    (setq inp (getstring spflag msg))
               )
          )
     )
     inp
)
;------------------------------------------------------------------
(defun ETOS (arg / file)
     (if (= 'STR (type arg)) (setq arg (strcat "\"" arg "\"")))
     (setq file (open "TL" "w"))
     (princ arg file)
     (close file)
     (setq file (open "TL" "r"))
     (setq arg (read-line file))
     (close file)
     (close (open "TL" "w"))
     arg
)  
;------------------------------------------------------------------
(defun DXF (code elist)
     (cdr (assoc code elist))
)
;-------------------------------------------------------------
(defun Text_get ( / ssl  nsset temp ed )
     (setq #sset (ssget))
     (setq ssl (sslength #sset) 
           nsset (ssadd)
     )
     (print ssl)
     (princ "entities found. ")  
     (princ "\nVerifying the selected entities -- please wait. ")
     (while (> ssl 0)
	     (progn
                 (setq temp (ssname #sset (setq ssl (1- ssl))))
                 (setq ed (entget temp))
                 (if (= (DXF 0 ed) "TEXT")
			(ssadd temp nsset)
		 )
            )
     )
     (setq ssl (sslength nsset)
           #sset nsset
     )
     (print ssl)
     (princ "TEXT entities found. ")
);defun Text_get1
;-------------------------------------------------------------
(prompt "\n		CC:Change code BigFont -> VNI; BK1 <-> VNI")
(defun c:CC ( / ssl temp ed  old new )
     (setq Code1 (getint "\nSource code <BF=1 / BK1=2 / VNI=3>: "))
     (setq Code2 (getint "\nDestination code <BF=1 / BK1=2 / VNI=3>: "))
     (Text_get)

     (setq ssl (sslength #sset))
     (while (> ssl 0)
          (progn
               (setq temp (ssname #sset (setq ssl (1- ssl)))
                     ed (entget temp)
                     old (cons 1 (DXF 1 ed))
                     #txt (DXF 1 ed)
               )
               (ChangeCode Code1 Code2 )
               (setq new (cons 1 #txt)
                     ed (subst new old ed)
               )
  	       (setq old (cons 7 (DXF 7 ed)))
	       (if (= Code2 3) (setq new (cons 7 "2") ed (subst new old ed)))
          )
          (entmod ed)  
     )
     (princ)
);defun
;-------------------------------------------------------------------
(defun ChangeCode ( Code1 code2 / char char1 len txt1 i )
     (setq txt1 "")
     (setq len (strlen #txt))
     (setq i 1)
     
     (if (AND (= Code1 2) (= Code2 3)) ;   BK1 -> VNI
          (progn
               (repeat len
                    (setq char (substr #txt i 1))
                    (cond
                         ((= (ascii char) 125) (setq char "Ñ"))
                         
                         ((= (ascii char) 123) (setq char "YÙ")) 
                         ((= (ascii char) 94) (setq char "YØ"))
                         ((= (ascii char) 96) (setq char "YÛ"))
                         ((= (ascii char) 124) (setq char "YÕ"))
                         ((= (ascii char) 127) (setq char "Î"))
                         
                         ((= (ascii char) 128) (setq char "AÙ"))
                         ((= (ascii char) 129) (setq char "AØ"))
                         ((= (ascii char) 130) (setq char "AÛ"))
                         ((= (ascii char) 131) (setq char "AÕ"))
                         ((= (ascii char) 132) (setq char "AÏ"))
                         
                         ((= (ascii char) 133) (setq char "EÙ"))
                         ((= (ascii char) 134) (setq char "EØ"))
                         ((= (ascii char) 135) (setq char "EÛ"))
                         ((= (ascii char) 136) (setq char "EÕ"))
                         ((= (ascii char) 137) (setq char "EÏ"))
                         
                         ((= (ascii char) 138) (setq char "Í"))
                         ((= (ascii char) 139) (setq char "Ì"))
                         ((= (ascii char) 140) (setq char "Æ"))
                         ((= (ascii char) 141) (setq char "Ó"))
                         ((= (ascii char) 142) (setq char "Ò"))
                         
                         ((= (ascii char) 143) (setq char "OÙ"))
                         ((= (ascii char) 144) (setq char "OØ"))
                         ((= (ascii char) 145) (setq char "OÛ"))
                         ((= (ascii char) 146) (setq char "OÕ"))
                         ((= (ascii char) 147) (setq char "OÏ"))
                         
                         ((= (ascii char) 148) (setq char "UÙ"))
                         ((= (ascii char) 149) (setq char "UØ"))
                         ((= (ascii char) 150) (setq char "UÛ"))
                         ((= (ascii char) 151) (setq char "UÕ"))
                         ((= (ascii char) 152) (setq char "UÏ"))
                         
                         ((= (ascii char) 153) (setq char "AÊ"))
                         ((= (ascii char) 154) (setq char "AÉ"))
                         ((= (ascii char) 155) (setq char "AÈ"))
                         ((= (ascii char) 156) (setq char "AÚ"))
                         ((= (ascii char) 157) (setq char "AÜ"))
                         ((= (ascii char) 158) (setq char "AË"))
                         
                         ((= (ascii char) 159) (setq char "AÂ"))
                         ((= (ascii char) 126) (setq char "AÁ"))
                         ((= (ascii char) 161) (setq char "AÀ"))
                         ((= (ascii char) 162) (setq char "AÅ"))
                         ((= (ascii char) 163) (setq char "AÃ"))
                         ((= (ascii char) 164) (setq char "AÄ"))
                         
                         ((= (ascii char) 165) (setq char "EÂ"))
                         ((= (ascii char) 166) (setq char "EÁ"))
                         ((= (ascii char) 167) (setq char "EÀ"))
                         ((= (ascii char) 168) (setq char "EÅ"))
                         ((= (ascii char) 169) (setq char "EÃ"))
                         ((= (ascii char) 170) (setq char "EÄ"))
                         
                         ((= (ascii char) 171) (setq char "OÂ"))
                         ((= (ascii char) 172) (setq char "OÁ"))
                         ((= (ascii char) 173) (setq char "OÀ"))
                         ((= (ascii char) 174) (setq char "OÅ"))
                         ((= (ascii char) 175) (setq char "OÃ"))
                         ((= (ascii char) 176) (setq char "OÄ"))
                         
                         ((= (ascii char) 177) (setq char "Ô"))
                         ((= (ascii char) 178) (setq char "ÔÙ"))
                         ((= (ascii char) 179) (setq char "ÔØ"))
                         ((= (ascii char) 180) (setq char "ÔÛ"))
                         ((= (ascii char) 181) (setq char "ÔÕ"))
                         ((= (ascii char) 182) (setq char "ÔÏ"))
                         
                         ((= (ascii char) 183) (setq char "Ö"))
                         ((= (ascii char) 184) (setq char "ÖÙ"))
                         ((= (ascii char) 185) (setq char "ÖØ"))
                         ((= (ascii char) 186) (setq char "ÖÛ"))
                         ((= (ascii char) 187) (setq char "ÖÕ"))
                         ((= (ascii char) 188) (setq char "ÖÏ"))
                         
                         ((= (ascii char) 189) (setq char "ñ"))
                         
                         ((= (ascii char) 190) (setq char "aù"))
                         ((= (ascii char) 191) (setq char "aø"))
                         ((= (ascii char) 192) (setq char "aû"))
                         ((= (ascii char) 193) (setq char "aõ"))
                         ((= (ascii char) 194) (setq char "aï"))
                         
                         ((= (ascii char) 195) (setq char "eù"))
                         ((= (ascii char) 196) (setq char "eø"))
                         ((= (ascii char) 197) (setq char "eû"))
                         ((= (ascii char) 198) (setq char "eõ"))
                         ((= (ascii char) 199) (setq char "eï"))
                         
                         ((= (ascii char) 200) (setq char "í"))
                         ((= (ascii char) 201) (setq char "ì"))
                         ((= (ascii char) 202) (setq char "æ"))
                         ((= (ascii char) 203) (setq char "ó"))
                         ((= (ascii char) 204) (setq char "ò"))
                         
                         ((= (ascii char) 205) (setq char "où"))
                         ((= (ascii char) 206) (setq char "oø"))
                         ((= (ascii char) 207) (setq char "oû"))
                         ((= (ascii char) 208) (setq char "oõ"))
                         ((= (ascii char) 209) (setq char "oï"))
                         
                         ((= (ascii char) 210) (setq char "uù"))
                         ((= (ascii char) 211) (setq char "uø"))
                         ((= (ascii char) 212) (setq char "uû"))
                         ((= (ascii char) 213) (setq char "uõ"))
                         ((= (ascii char) 214) (setq char "uï"))
                         
                         ((= (ascii char) 215) (setq char "aê"))
                         ((= (ascii char) 216) (setq char "aé"))
                         ((= (ascii char) 217) (setq char "aè"))
                         ((= (ascii char) 218) (setq char "aú"))
                         ((= (ascii char) 219) (setq char "aü"))
                         ((= (ascii char) 220) (setq char "aë"))
                         
                         ((= (ascii char) 221) (setq char "aâ"))
                         ((= (ascii char) 222) (setq char "aá"))
                         ((= (ascii char) 223) (setq char "aà"))
                         ((= (ascii char) 224) (setq char "aå"))
                         ((= (ascii char) 225) (setq char "aã"))
                         ((= (ascii char) 226) (setq char "aä"))
                         
                         ((= (ascii char) 227) (setq char "eâ"))
                         ((= (ascii char) 228) (setq char "eá"))
                         ((= (ascii char) 229) (setq char "eà"))
                         ((= (ascii char) 230) (setq char "eå"))
                         ((= (ascii char) 231) (setq char "eã"))
                         ((= (ascii char) 232) (setq char "eä"))
                         
                         ((= (ascii char) 233) (setq char "oâ"))
                         ((= (ascii char) 234) (setq char "oá"))
                         ((= (ascii char) 235) (setq char "oà"))
                         ((= (ascii char) 236) (setq char "oå"))
                         ((= (ascii char) 237) (setq char "oã"))
                         ((= (ascii char) 238) (setq char "oä"))
                         
                         ((= (ascii char) 239) (setq char "ô"))
                         ((= (ascii char) 240) (setq char "ôù"))
                         ((= (ascii char) 241) (setq char "ôø"))
                         ((= (ascii char) 242) (setq char "ôû"))
                         ((= (ascii char) 243) (setq char "ôõ"))
                         ((= (ascii char) 244) (setq char "ôï"))
                         
                         ((= (ascii char) 245) (setq char "ö"))
                         ((= (ascii char) 246) (setq char "öù"))
                         ((= (ascii char) 247) (setq char "öø"))
                         ((= (ascii char) 248) (setq char "öû"))
                         ((= (ascii char) 249) (setq char "öõ"))
                         ((= (ascii char) 250) (setq char "öï"))
                         
                         ((= (ascii char) 251) (setq char "yù"))
                         ((= (ascii char) 252) (setq char "yø"))
                         ((= (ascii char) 253) (setq char "yû"))
                         ((= (ascii char) 254) (setq char "yõ"))
                         ((= (ascii char) 255) (setq char "î"))
                        
                    );cond
                    (setq i (+ i 1))
                    (setq txt1 (strcat txt1 char))
               );repeat
          );progn
     ) ;if
     
     (if (AND (= Code1 3) (= Code2 2)) ; VNI -> BK1
          (progn
               (repeat len
                    (setq char (substr #txt i 1))
                    (setq char1 (substr #txt (+ i 1) 1))
                    (cond
                         ((AND (= (ascii char1) 217) (= char "Y")) (setq char (chr 123) i (+ i 2))) 
                         ((AND (= (ascii char1) 217) (= char "A")) (setq char (chr 128) i (+ i 2))) 
                         ((AND (= (ascii char1) 217) (= char "E")) (setq char (chr 133) i (+ i 2))) 
                         ((AND (= (ascii char1) 217) (= char "O")) (setq char (chr 143) i (+ i 2))) 
                         ((AND (= (ascii char1) 217) (= char "U")) (setq char (chr 148) i (+ i 2))) 
                         ((AND (= (ascii char1) 217) (= char "Ô")) (setq char (chr 178) i (+ i 2))) 
                         ((AND (= (ascii char1) 217) (= char "Ö")) (setq char (chr 184) i (+ i 2))) 
                         
                         ((AND (= (ascii char1) 216) (= char "Y")) (setq char (chr 94) i (+ i 2))) 
                         ((AND (= (ascii char1) 216) (= char "A")) (setq char (chr 129) i (+ i 2))) 
                         ((AND (= (ascii char1) 216) (= char "E")) (setq char (chr 134) i (+ i 2))) 
                         ((AND (= (ascii char1) 216) (= char "O")) (setq char (chr 144) i (+ i 2))) 
                         ((AND (= (ascii char1) 216) (= char "U")) (setq char (chr 149) i (+ i 2))) 
                         ((AND (= (ascii char1) 216) (= char "Ô")) (setq char (chr 179) i (+ i 2))) 
                         ((AND (= (ascii char1) 216) (= char "Ö")) (setq char (chr 185) i (+ i 2))) 
                         
                         ((AND (= (ascii char1) 219) (= char "Y")) (setq char (chr 96) i (+ i 2))) 
                         ((AND (= (ascii char1) 219) (= char "A")) (setq char (chr 130) i (+ i 2))) 
                         ((AND (= (ascii char1) 219) (= char "E")) (setq char (chr 135) i (+ i 2))) 
                         ((AND (= (ascii char1) 219) (= char "O")) (setq char (chr 145) i (+ i 2))) 
                         ((AND (= (ascii char1) 219) (= char "U")) (setq char (chr 150) i (+ i 2))) 
                         ((AND (= (ascii char1) 219) (= char "Ô")) (setq char (chr 180) i (+ i 2))) 
                         ((AND (= (ascii char1) 219) (= char "Ö")) (setq char (chr 186) i (+ i 2))) 
                         
                         ((AND (= (ascii char1) 213) (= char "Y")) (setq char (chr 124) i (+ i 2))) 
                         ((AND (= (ascii char1) 213) (= char "A")) (setq char (chr 131) i (+ i 2))) 
                         ((AND (= (ascii char1) 213) (= char "E")) (setq char (chr 136) i (+ i 2))) 
                         ((AND (= (ascii char1) 213) (= char "O")) (setq char (chr 146) i (+ i 2))) 
                         ((AND (= (ascii char1) 213) (= char "U")) (setq char (chr 151) i (+ i 2))) 
                         ((AND (= (ascii char1) 213) (= char "Ô")) (setq char (chr 181) i (+ i 2))) 
                         ((AND (= (ascii char1) 213) (= char "Ö")) (setq char (chr 187) i (+ i 2))) 
                         
                         ((AND (= (ascii char1) 207) (= char "A")) (setq char (chr 132) i (+ i 2))) 
                         ((AND (= (ascii char1) 207) (= char "E")) (setq char (chr 137) i (+ i 2))) 
                         ((AND (= (ascii char1) 207) (= char "O")) (setq char (chr 147) i (+ i 2))) 
                         ((AND (= (ascii char1) 207) (= char "U")) (setq char (chr 152) i (+ i 2))) 
                         ((AND (= (ascii char1) 207) (= char "Ô")) (setq char (chr 182) i (+ i 2))) 
                         ((AND (= (ascii char1) 207) (= char "Ö")) (setq char (chr 188) i (+ i 2))) 
                         
                         ((AND (= (ascii char1) 202) (= char "A")) (setq char (chr 153) i (+ i 2))) 
                         ((AND (= (ascii char1) 201) (= char "A")) (setq char (chr 154) i (+ i 2))) 
                         ((AND (= (ascii char1) 200) (= char "A")) (setq char (chr 155) i (+ i 2))) 
                         ((AND (= (ascii char1) 218) (= char "A")) (setq char (chr 156) i (+ i 2))) 
                         ((AND (= (ascii char1) 220) (= char "A")) (setq char (chr 157) i (+ i 2))) 
                         ((AND (= (ascii char1) 203) (= char "A")) (setq char (chr 158) i (+ i 2))) 
                         
                         ((AND (= (ascii char1) 194) (= char "A")) (setq char (chr 159) i (+ i 2))) 
                         ((AND (= (ascii char1) 193) (= char "A")) (setq char (chr 126) i (+ i 2))) 
                         ((AND (= (ascii char1) 192) (= char "A")) (setq char (chr 161) i (+ i 2))) 
                         ((AND (= (ascii char1) 197) (= char "A")) (setq char (chr 162) i (+ i 2))) 
                         ((AND (= (ascii char1) 195) (= char "A")) (setq char (chr 163) i (+ i 2))) 
                         ((AND (= (ascii char1) 196) (= char "A")) (setq char (chr 164) i (+ i 2))) 
                         
                         ((AND (= (ascii char1) 194) (= char "E")) (setq char (chr 165) i (+ i 2))) 
                         ((AND (= (ascii char1) 193) (= char "E")) (setq char (chr 166) i (+ i 2))) 
                         ((AND (= (ascii char1) 192) (= char "E")) (setq char (chr 167) i (+ i 2))) 
                         ((AND (= (ascii char1) 197) (= char "E")) (setq char (chr 168) i (+ i 2))) 
                         ((AND (= (ascii char1) 195) (= char "E")) (setq char (chr 169) i (+ i 2))) 
                         ((AND (= (ascii char1) 196) (= char "E")) (setq char (chr 170) i (+ i 2))) 
                         
                         ((AND (= (ascii char1) 194) (= char "O")) (setq char (chr 171) i (+ i 2))) 
                         ((AND (= (ascii char1) 193) (= char "O")) (setq char (chr 172) i (+ i 2))) 
                         ((AND (= (ascii char1) 192) (= char "O")) (setq char (chr 173) i (+ i 2))) 
                         ((AND (= (ascii char1) 197) (= char "O")) (setq char (chr 174) i (+ i 2))) 
                         ((AND (= (ascii char1) 195) (= char "O")) (setq char (chr 175) i (+ i 2))) 
                         ((AND (= (ascii char1) 196) (= char "O")) (setq char (chr 176) i (+ i 2))) 
                         
                         ((AND (= (ascii char1) 249) (= char "a")) (setq char (chr 190) i (+ i 2))) 
                         ((AND (= (ascii char1) 248) (= char "a")) (setq char (chr 191) i (+ i 2))) 
                         ((AND (= (ascii char1) 251) (= char "a")) (setq char (chr 192) i (+ i 2))) 
                         ((AND (= (ascii char1) 245) (= char "a")) (setq char (chr 193) i (+ i 2))) 
                         ((AND (= (ascii char1) 239) (= char "a")) (setq char (chr 194) i (+ i 2))) 
                         
                         ((AND (= (ascii char1) 249) (= char "e")) (setq char (chr 195) i (+ i 2))) 
                         ((AND (= (ascii char1) 248) (= char "e")) (setq char (chr 196) i (+ i 2))) 
                         ((AND (= (ascii char1) 251) (= char "e")) (setq char (chr 197) i (+ i 2))) 
                         ((AND (= (ascii char1) 245) (= char "e")) (setq char (chr 198) i (+ i 2))) 
                         ((AND (= (ascii char1) 239) (= char "e")) (setq char (chr 199) i (+ i 2))) 
                         
                         ((AND (= (ascii char1) 249) (= char "o")) (setq char (chr 205) i (+ i 2))) 
                         ((AND (= (ascii char1) 248) (= char "o")) (setq char (chr 206) i (+ i 2))) 
                         ((AND (= (ascii char1) 251) (= char "o")) (setq char (chr 207) i (+ i 2))) 
                         ((AND (= (ascii char1) 245) (= char "o")) (setq char (chr 208) i (+ i 2))) 
                         ((AND (= (ascii char1) 239) (= char "o")) (setq char (chr 209) i (+ i 2))) 
                         
                         ((AND (= (ascii char1) 249) (= char "u")) (setq char (chr 210) i (+ i 2))) 
                         ((AND (= (ascii char1) 248) (= char "u")) (setq char (chr 211) i (+ i 2))) 
                         ((AND (= (ascii char1) 251) (= char "u")) (setq char (chr 212) i (+ i 2))) 
                         ((AND (= (ascii char1) 245) (= char "u")) (setq char (chr 213) i (+ i 2))) 
                         ((AND (= (ascii char1) 239) (= char "u")) (setq char (chr 214) i (+ i 2))) 
                         
                         ((AND (= (ascii char1) 234) (= char "a")) (setq char (chr 215) i (+ i 2))) 
                         ((AND (= (ascii char1) 233) (= char "a")) (setq char (chr 216) i (+ i 2))) 
                         ((AND (= (ascii char1) 232) (= char "a")) (setq char (chr 217) i (+ i 2))) 
                         ((AND (= (ascii char1) 250) (= char "a")) (setq char (chr 218) i (+ i 2))) 
                         ((AND (= (ascii char1) 252) (= char "a")) (setq char (chr 219) i (+ i 2))) 
                         ((AND (= (ascii char1) 235) (= char "a")) (setq char (chr 220) i (+ i 2))) 
                         
                         ((AND (= (ascii char1) 226) (= char "a")) (setq char (chr 221) i (+ i 2))) 
                         ((AND (= (ascii char1) 225) (= char "a")) (setq char (chr 222) i (+ i 2))) 
                         ((AND (= (ascii char1) 224) (= char "a")) (setq char (chr 223) i (+ i 2))) 
                         ((AND (= (ascii char1) 229) (= char "a")) (setq char (chr 224) i (+ i 2))) 
                         ((AND (= (ascii char1) 227) (= char "a")) (setq char (chr 225) i (+ i 2))) 
                         ((AND (= (ascii char1) 228) (= char "a")) (setq char (chr 226) i (+ i 2))) 
                         
                         ((AND (= (ascii char1) 226) (= char "e")) (setq char (chr 227) i (+ i 2))) 
                         ((AND (= (ascii char1) 225) (= char "e")) (setq char (chr 228) i (+ i 2))) 
                         ((AND (= (ascii char1) 224) (= char "e")) (setq char (chr 229) i (+ i 2))) 
                         ((AND (= (ascii char1) 229) (= char "e")) (setq char (chr 230) i (+ i 2))) 
                         ((AND (= (ascii char1) 227) (= char "e")) (setq char (chr 231) i (+ i 2))) 
                         ((AND (= (ascii char1) 228) (= char "e")) (setq char (chr 232) i (+ i 2))) 
                         
                         ((AND (= (ascii char1) 226) (= char "o")) (setq char (chr 233) i (+ i 2))) 
                         ((AND (= (ascii char1) 225) (= char "o")) (setq char (chr 234) i (+ i 2))) 
                         ((AND (= (ascii char1) 224) (= char "o")) (setq char (chr 235) i (+ i 2))) 
                         ((AND (= (ascii char1) 229) (= char "o")) (setq char (chr 236) i (+ i 2))) 
                         ((AND (= (ascii char1) 227) (= char "o")) (setq char (chr 237) i (+ i 2))) 
                         ((AND (= (ascii char1) 228) (= char "o")) (setq char (chr 238) i (+ i 2))) 
                         
                         ((AND (= (ascii char1) 249) (= char "ô")) (setq char (chr 240) i (+ i 2))) 
                         ((AND (= (ascii char1) 248) (= char "ô")) (setq char (chr 241) i (+ i 2))) 
                         ((AND (= (ascii char1) 251) (= char "ô")) (setq char (chr 242) i (+ i 2))) 
                         ((AND (= (ascii char1) 245) (= char "ô")) (setq char (chr 243) i (+ i 2))) 
                         ((AND (= (ascii char1) 239) (= char "ô")) (setq char (chr 244) i (+ i 2))) 
                         
                         ((AND (= (ascii char1) 249) (= char "ö")) (setq char (chr 246) i (+ i 2))) 
                         ((AND (= (ascii char1) 248) (= char "ö")) (setq char (chr 247) i (+ i 2))) 
                         ((AND (= (ascii char1) 251) (= char "ö")) (setq char (chr 248) i (+ i 2))) 
                         ((AND (= (ascii char1) 245) (= char "ö")) (setq char (chr 249) i (+ i 2))) 
                         ((AND (= (ascii char1) 239) (= char "ö")) (setq char (chr 250) i (+ i 2))) 
                         
                         ((AND (= (ascii char1) 249) (= char "y")) (setq char (chr 251) i (+ i 2))) 
                         ((AND (= (ascii char1) 248) (= char "y")) (setq char (chr 252) i (+ i 2))) 
                         ((AND (= (ascii char1) 251) (= char "y")) (setq char (chr 253) i (+ i 2))) 
                         ((AND (= (ascii char1) 245) (= char "y")) (setq char (chr 254) i (+ i 2))) 
                         
                         ((= char "Ñ") (setq char (chr 125) i (+ i 1)))
                         ((= char "Î") (setq char (chr 127) i (+ i 1)))
                         ((= char "Í")  (setq char (chr 138) i (+ i 1)))
                         ((= char "Ì")  (setq char (chr 139) i (+ i 1)))
                         ((= char "Æ")  (setq char (chr 140) i (+ i 1)))
                         ((= char "Ó")  (setq char (chr 141) i (+ i 1)))
                         ((= char "Ò")  (setq char (chr 142) i (+ i 1)))
                         ((= char "Ô") (setq char (chr 177) i (+ i 1)))
                         ((= char "Ö") (setq char (chr 183) i (+ i 1)))
                         ((= char "ñ") (setq char (chr 189) i (+ i 1)))
                         ((= char "í") (setq char (chr 200) i (+ i 1)))
                         ((= char "ì") (setq char (chr 201) i (+ i 1)))
                         ((= char "æ") (setq char (chr 202) i (+ i 1)))
                         ((= char "ó") (setq char (chr 203) i (+ i 1)))
                         ((= char "ò") (setq char (chr 204) i (+ i 1)))
                         ((= char "ô") (setq char (chr 239) i (+ i 1)))
                         ((= char "ö") (setq char (chr 245) i (+ i 1)))
                         ((= char "î") (setq char (chr 238) i (+ i 1)))
                         
                         ((setq i (+ i 1)))
                    );cond
                    (setq txt1 (strcat txt1 char))
               );repeat
          );progn
     ) ;if
   
(if (AND (= Code1 1) (= Code2 3)) ;   BIG -> VNI
   (progn
      (setq #txt (strcase #txt))
      (while (<= i len)
         (setq chars (substr #txt i 5)
            char (substr #txt i 1)
            test 0
         )
         (cond
            ;;;;;;;;;(LOAI 2 DAU CUA A)
            ((OR (= chars "`1`6A") (= chars "`6`1A")) (setq chars "AÁ" test 1))                     
            ((OR (= chars "`2`6A") (= chars "`6`2A")) (setq chars "AÀ" test 1))
            ((OR (= chars "`3`6A") (= chars "`6`3A")) (setq chars "AÅ" test 1))                          
            ((OR (= chars "`4`6A") (= chars "`6`4A")) (setq chars "AÃ" test 1))
            ((OR (= chars "`5`6A") (= chars "`6`5A")) (setq chars "AÄ" test 1))
            ;;;;;;;;;;;
            ((OR (= chars "`1`8A") (= chars "`8`1A")) (setq chars "AÉ" test 1))                     
            ((OR (= chars "`2`8A") (= chars "`8`2A")) (setq chars "AÈ" test 1))
            ((OR (= chars "`3`8A") (= chars "`8`3A")) (setq chars "AÚ" test 1))                          
            ((OR (= chars "`4`8A") (= chars "`8`4A")) (setq chars "AÜ" test 1))
            ((OR (= chars "`5`8A") (= chars "`8`5A")) (setq chars "AË" test 1))
            ;;;;;;;;;(LOAI 2 DAU CUA O)
            ((OR (= chars "`1`6O") (= chars "`6`1O")) (setq chars "OÁ" test 1))                     
            ((OR (= chars "`2`6O") (= chars "`6`2O")) (setq chars "OÀ" test 1))
            ((OR (= chars "`3`6O") (= chars "`6`3O")) (setq chars "OÅ" test 1))                          
            ((OR (= chars "`4`6O") (= chars "`6`4O")) (setq chars "OÃ" test 1))
            ((OR (= chars "`5`6O") (= chars "`6`5O")) (setq chars "OÄ" test 1))
            ;;;;;;;;;;;
            ((OR (= chars "`1`7O") (= chars "`7`1O")) (setq chars "ÔÙ" test 1))                     
            ((OR (= chars "`2`7O") (= chars "`7`2O")) (setq chars "ÔØ" test 1))
            ((OR (= chars "`3`7O") (= chars "`7`3O")) (setq chars "ÔÛ" test 1))                          
            ((OR (= chars "`4`7O") (= chars "`7`4O")) (setq chars "ÔÕ" test 1))
            ((OR (= chars "`5`7O") (= chars "`7`5O")) (setq chars "ÔÏ" test 1))
            ;;;;;;;;;;;LOAI 2 DAU CUA U
            ((OR (= chars "`1`7U") (= chars "`7`1U")) (setq chars "ÖÙ" test 1))                     
            ((OR (= chars "`2`7U") (= chars "`7`2U")) (setq chars "ÖØ" test 1))
            ((OR (= chars "`3`7U") (= chars "`7`3U")) (setq chars "ÖÛ" test 1))                          
            ((OR (= chars "`4`7U") (= chars "`7`4U")) (setq chars "ÖÕ" test 1))
            ((OR (= chars "`5`7U") (= chars "`7`5U")) (setq chars "ÖÏ" test 1))
	     ;;;;;;;;;(LOAI 2 DAU CUA E)
            ((OR (= chars "`1`6E") (= chars "`6`1E")) (setq chars "EÁ" test 1))                     
            ((OR (= chars "`2`6E") (= chars "`6`2E")) (setq chars "EÀ" test 1))
            ((OR (= chars "`3`6E") (= chars "`6`3E")) (setq chars "EÅ" test 1))
            ((OR (= chars "`4`6E") (= chars "`6`4E")) (setq chars "EÃ" test 1))
            ((OR (= chars "`5`6E") (= chars "`6`5E")) (setq chars "EÄ" test 1))
            ;;;;;;;;;
         );cond
         (if (= test 1)
            (progn 
               (setq txt1 (strcat txt1 chars)) 
               (setq i (+ i 5))
            )
            (progn
               (setq txt1 (strcat txt1 char))
               (setq i (+ i 1))
            )
         )
      );while VOI CHU CO 2 DAU
      ;;;;;;;;;;;;;;;;;;;;;;;;;;;;;;;;
      (setq txt2 txt1)
      (setq len (strlen txt2))
      (setq i 1)
      (setq txt1 "")
      (while (<= i len)
         (setq chars (substr txt2 i 3)
            char (substr txt2 i 1)
            test 0
         )
         (cond
            ;;;;;;;;;(LOAI 1 DAU CUA A)
            ((= chars "`1A") (setq chars "AÙ" test 1))                     
            ((= chars "`2A") (setq chars "AØ" test 1))
            ((= chars "`3A") (setq chars "AÛ" test 1))                          
            ((= chars "`4A") (setq chars "AÕ" test 1))
            ((= chars "`5A") (setq chars "AÏ" test 1))
            ((= chars "`6A") (setq chars "AÂ" test 1))
            ((= chars "`8A") (setq chars "AÊ" test 1))
            ;;;;;;;;;(LOAI 1 DAU CUA O)
            ((= chars "`1O") (setq chars "OÙ" test 1))                     
            ((= chars "`2O") (setq chars "OØ" test 1))
            ((= chars "`3O") (setq chars "OÛ" test 1))                          
            ((= chars "`4O") (setq chars "OÕ" test 1))
            ((= chars "`5O") (setq chars "OÏ" test 1))
            ((= chars "`6O") (setq chars "OÂ" test 1))
            ((= chars "`7O") (setq chars  "Ô" test 1))
            ;;;;;;;;;(LOAI 1 DAU CUA E)
            ((= chars "`1E") (setq chars "EÙ" test 1))                     
            ((= chars "`2E") (setq chars "EØ" test 1))
            ((= chars "`3E") (setq chars "EÛ" test 1))                          
            ((= chars "`4E") (setq chars "EÕ" test 1))
            ((= chars "`5E") (setq chars "EÏ" test 1))
            ((= chars "`6E") (setq chars "EÂ" test 1))
            ;;;;;;;;;(LOAI 1 DAU CUA I)
            ((= chars "`1I") (setq chars "Í" test 1))                     
            ((= chars "`2I") (setq chars "Ì" test 1))
            ((= chars "`3I") (setq chars "Æ" test 1))                          
            ((= chars "`4I") (setq chars "Ó" test 1))
            ((= chars "`5I") (setq chars "Ò" test 1))
            ;;;;;;;;;(LOAI 1 DAU CUA Y)
            ((= chars "`1Y") (setq chars "YÙ" test 1))                     
            ((= chars "`2Y") (setq chars "YØ" test 1))
            ((= chars "`3Y") (setq chars "YÛ" test 1))                          
            ((= chars "`4Y") (setq chars "YÕ" test 1))
            ((= chars "`5Y") (setq chars  "Î" test 1))
            ;;;;;;;;;(LOAI 1 DAU CUA U)
            ((= chars "`1U") (setq chars "UÙ" test 1))                     
            ((= chars "`2U") (setq chars "UØ" test 1))
            ((= chars "`3U") (setq chars "UÛ" test 1))                          
            ((= chars "`4U") (setq chars "UÕ" test 1))
            ((= chars "`5U") (setq chars "UÏ" test 1))
            ((= chars "`7U") (setq chars  "Ö" test 1))
             ;;;;;;;;;(LOAI 1 DAU CUA D)
            ((= chars "`9D") (setq chars  "Ñ" test 1))                     
            ;;;;;;;;;;;;;;;;;;;;;;;;;;;
            
         );cond
         (if (= test 1)
            (progn 
               (setq txt1 (strcat txt1 chars)) 
               (setq i (+ i 3))
            )
            (progn
               (setq txt1 (strcat txt1 char))
               (setq i (+ i 1))
            )
         )
      );while KHI CAC CHU CO 1 DAU

  );progn
);if BIG  
(setq #txt txt1)       
);defun ChangeCode
;-------------------------------------------------------------------

(defun USTR (bit msg def spflag / inp nval)
     (if (and def (/= def ""))
          (setq msg (strcat "\n" msg "<" def ">: ")
               inp (getstring spflag msg)
               inp (if (= inp "") def inp)
          )
          (progn
               (if (= " " (substr msg (strlen msg) 1))
                    (setq msg (strcat "\n" (substr msg 1 (1- (strlen msg))) ": "))
                    (setq msg (strcat "\n" msg ": "))
               )
               (if (= bit 1)
                    (while (= "" (setq inp (getstring spflag msg)))
                         (prompt "\nInvalid String.")
                    )
                    (setq inp (getstring spflag msg))
               )
          )
     )
     inp
)

Attribute VB_Name = "UserForm1"
Attribute VB_Base = "0{FF101186-90B8-43C4-8151-FEE40FF29955}{0F7D6317-6965-4714-BA2C-64BDE830C488}"
Attribute VB_GlobalNameSpace = False
Attribute VB_Creatable = False
Attribute VB_PredeclaredId = True
Attribute VB_Exposed = False
Attribute VB_TemplateDerived = False
Attribute VB_Customizable = False
Private Sub CommandButton1_Click()
Dim p
Dim style As AcadTextStyle
Dim text As AcadText
Set style = ThisDrawing.TextStyles.Add("2")
style.fontFile = "C:\Windows\FONTS\VN_vni.SHX"
style.Width = 0.75
UserForm1.Hide
p = ThisDrawing.Utility.RealToString(132456, acDecimal, 2)
MsgBox p
'Set text = ThisDrawing.ModelSpace.AddText("falsjkdf", p, 1.6)

text.StyleName = "2"

text.Update
'Set p = ThisDrawing.ModelSpace.AddLeader()
UserForm1.Show
'style.name = "2"
End Sub

Private Sub UserForm_Click()

End Sub

Attribute VB_Name = "frmTenBV"
Attribute VB_Base = "0{F290347D-3652-4188-B797-F70EC6592F67}{F3943287-03D3-4362-B7B2-BD08CA9734BE}"
Attribute VB_GlobalNameSpace = False
Attribute VB_Creatable = False
Attribute VB_PredeclaredId = True
Attribute VB_Exposed = False
Attribute VB_TemplateDerived = False
Attribute VB_Customizable = False
Dim aDOC As AcadDocument
Dim aUTI As AcadUtility
Dim aMS As AcadModelSpace
Dim aText As AcadText
Dim aSel As AcadSelectionSet
Dim StPoint As Variant
Dim Distance As Double

Private Sub cmdExit_Click()
    Unload Me
    End
End Sub

Private Sub cmdGetDist_Click()
    Me.Hide
    Distance = aUTI.GetDistance(, "Khoang cach de ghi:")
    txtDist = Distance
    Me.Show
End Sub

Private Sub cmdGetPoint_Click()
    Set aSel = aDOC.SelectionSets.Add("b")
    Me.Hide
    aDOC.SetVariable "OSMODE", 64
    StPoint = aUTI.GetPoint(, vbCrLf & "Chon chu lam mau:")
    aSel.SelectAtPoint StPoint
    Set aText = aSel(0)
    txtX = StPoint(0)
    txtY = StPoint(1)
    txtZ = StPoint(2)
    txtStyle = aText.StyleName
    txtTextH = aText.Height
    aSel.Delete
    Set aSel = Nothing
    Me.Show
End Sub

Private Sub cmdOK_Click()
    '
    Dim n As Integer, i As Integer
    Dim x As Double
    Dim Dst As Double
    Dim InsPt(0 To 2) As Double
'    aDOC.ActiveTextStyle = aDOC.TextStyles(txtStyle)
    '
    n = txtQuantity.text
    x = txtX
    InsPt(1) = txtY
    InsPt(2) = txtZ
    Dst = txtDist
    '
    Me.Hide
    For i = 0 To n - 1
        InsPt(0) = i * Dst + x
        Set aText = aMS.AddText(lstName.List(i), InsPt, txtTextH)
        aText.Alignment = acAlignmentCenter
        aText.ScaleFactor = 1
        aText.StyleName = txtStyle
        aText.Move aText.InsertionPoint, InsPt
        aText.Update
    Next i
    Unload Me
    End
    '
End Sub

Private Sub CommandButton1_Click()
    '
    Dim start As Integer
    Dim i As Integer, n As Integer
    Dim steps As Integer
    Dim prefix As String
    Dim suffix As String
    Dim name As String
    Dim lens As Integer
    '
    start = txtStart.text
    steps = txtStep.text
    n = txtQuantity.text - 1
    prefix = txtPre.text
    suffix = txtPos.text
    lens = Len(txtName.text)
    '
    lstName.Clear
    For i = 0 To n 'Step steps
        
        name = i * steps + start
        If Len(name) < lens Then _
            name = prefix & String(lens - Len(name), "0") & name & suffix _
        Else name = prefix & name & suffix
        lstName.AddItem
        lstName.List(i) = name
        
    Next i
    '
End Sub

Private Sub UserForm_Initialize()
    Set aDOC = ThisDrawing
    Set aUTI = ThisDrawing.Utility
    Set aMS = ThisDrawing.ModelSpace
'    txtValue = "###0"
'    txtStart = 1
'    txtStep = 1
End Sub

Private Sub UserForm_Terminate()
    Set aDOC = Nothing
    Set aUTI = Nothing
    Set aMS = Nothing
End Sub

Attribute VB_Name = "modACADGenerated"
Option Explicit

Const pi = 3.14159265358979

Sub Sort_Text(aTexts() As AcadText)

    Dim i As Integer, j As Integer
    Dim at As AcadText
    Dim n As Integer
    Dim x1, x2
    n = UBound(aTexts()) - 1
    For i = 0 To n - 1
      For j = i + 1 To n
            x1 = aTexts(i).InsertionPoint(0)
            x2 = aTexts(j).InsertionPoint(0)
            If x1 > x2 Then
                Set at = aTexts(i)
                Set aTexts(i) = aTexts(j)
                Set aTexts(j) = at
            End If
        Next j
    Next i
End Sub
Function TextMax(aTexts() As AcadText) As Double
    Dim i As Integer, j As Integer
    Dim at As AcadText
    Dim n As Integer
    Dim Tmax  As Double
    n = UBound(aTexts()) - 1
    Tmax = Val(aTexts(0).TextString)
    For i = 0 To n
            If Tmax < Val(aTexts(i).TextString) Then
                Tmax = Val(aTexts(i).TextString)
            End If
    Next i
    TextMax = Tmax
End Function

Attribute VB_Name = "modNEW2"

Sub Sort_Text2(aTexts() As AcadText)

    Dim i As Integer, j As Integer, n As Integer
    Dim at As AcadText
    Dim y1, y2, x1, x2
    n = UBound(aTexts)
    For i = 0 To n - 1
        For j = i To n
            x1 = aTexts(i).InsertionPoint(0)
            x2 = aTexts(j).InsertionPoint(0)
            y1 = aTexts(i).InsertionPoint(1)
            y2 = aTexts(j).InsertionPoint(1)
            If (y1 < y2) Or ((x1 > x2) And (y1 = y2)) Then
                Set at = aTexts(i)
                Set aTexts(i) = aTexts(j)
                Set aTexts(j) = at
            End If
        Next j
    Next i
    For i = 0 To n - 1
        If (i Mod 5 = 4) Then
            Set at = aTexts(i)
            Set aTexts(i) = aTexts(i + 1)
            Set aTexts(i + 1) = at
        End If
    Next
End Sub

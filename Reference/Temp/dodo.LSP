(Defun c:dodo ( )
(command "undo" "be")
  (setq luubatdiem (getvar "osmode"))  
  (setvar "osmode" 0)
(setq ddd (entsel "\nChon text thu nhat"))
(while
 (or
   (null ddd)
   (/= "TEXT" (cdr (assoc 0 (entget (car ddd)))))
)
(princ "\nDoi tuong khong phai la text! Chon lai")
(setq ddd (entsel "\nChon text mau"))
)
   (setq DT (car ddd))
   (setq DT (entget DT))
   (setq TEXT (cdr (assoc 1 DT)))
   (setq di1 (cdr (assoc 11 DT)))
   (setq giatri (atof TEXT)) 
;;;;;;;;;;
(setq ddd (entsel "\nChon text thu hai"))
(while
 (or
   (null ddd)
   (/= "TEXT" (cdr (assoc 0 (entget (car ddd)))))
)
(princ "\nDoi tuong khong phai la text! Chon lai")
(setq ddd (entsel "\nChon text mau"))
)
   (setq DT (car ddd))
   (setq DT (entget DT))
   (setq TEXT (cdr (assoc 1 DT)))
   (setq di2 (cdr (assoc 11 DT)))
   (setq docao (cdr (assoc 40 DT)))
   (setq giatri1 (atof TEXT)) 
;;;;;;;;;;;;
   (setq gialech (- giatri giatri1))
   (setq giatril (distance di1 di2))
   (setq dodoc (/ gialech giatril)) 
   (setq noidungviet (strcat "L=" (rtos giatril 2 2)))
   (setq noidungvietd (strcat "i=" (rtos dodoc 2 2) "%"))
   (setq di3 (list (/ (+ (car di1) (car di2)) 2) (/ (+ (cadr di1) (cadr di2)) 2)))
   (setq nuadoan (* (/ docao 3) 2))
   (setq di4 (list (car di3) (+ (cadr di3) nuadoan)))
   (setq di5 (list (car di3) (- (cadr di3) nuadoan)))
 (command ".copy" DDD "" di2 di4)
   (setq DTDM (entlast))
   (setq Elist (entget DTDM)) 
   (setq Oldlist (assoc 1 Elist)) 
   (setq Oldtext (cdr Oldlist))
   (setq Oldtext (strcase Oldtext nil))
   (setq Newlist (cons '1 noidungviet))
   (setq Elist (subst Newlist Oldlist Elist))
   (entmod Elist)

 (command ".copy" DDD "" di2 di5)
   (setq DTDM (entlast))
   (setq Elist (entget DTDM)) 
   (setq Oldlist (assoc 1 Elist)) 
   (setq Oldtext (cdr Oldlist))
   (setq Oldtext (strcase Oldtext nil))
   (setq Newlist (cons '1 noidungvietd))
   (setq Elist (subst Newlist Oldlist Elist))
   (entmod Elist)


(setvar "osmode" luubatdiem) 
(command "undo" "end")
(setvar "MODEMACRO" "**duy782006.blogspot.com**")
    (Princ)
)

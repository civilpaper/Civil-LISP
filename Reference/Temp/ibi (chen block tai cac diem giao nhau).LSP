(defun LM:IntersectionsinSet (ss / a b i j l)
  (setq i (sslength ss))
  (while (not (minusp (setq j (1- i)
			    i (1- i)
		      )
	      )
	 )
    (setq a (vlax-ename->vla-object (ssname ss i)))
    (while (not (minusp (setq j (1- j))))
      (setq b (vlax-ename->vla-object (ssname ss j))
	    l (cons (LM:GroupByNum
		      (vlax-invoke a 'IntersectWith b acExtendNone)
		      3
		    )
		    l
	      )
      )
    )
  )
  (apply 'append l)
)
(defun LM:GroupByNum (l n / r)
  (if l
    (cons (reverse (repeat n
		     (setq r (cons (car l) r)
			   l (cdr l)
		     )
		     r
		   )
	  )
	  (LM:GroupByNum l n)
    )
  )
)
(defun dxf (code e) (cdr (assoc code (entget e))))
(defun C:ibi (/ os ss lst en pt item)
  (setq os (getvar "osmode"))
  (setvar "osmode" 0)
  (princ "\n Chon cac doi tuong giao nhau")
  (setq	ss  (ssget)
	lst (LM:IntersectionsinSet ss)
	en  (car (entsel "\nChon Block"))
	pt  (dxf 10 en)
  )
  (foreach item lst (command "copy" en "" pt item))
  (setvar "osmode" os)
)

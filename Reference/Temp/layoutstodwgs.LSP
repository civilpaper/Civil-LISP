(defun c:layoutstodwgs (/ fda pre l exprt ct lays msg doc)
  (setq	fda   (getvar 'filedia)
	pre   (getstring "\n Enter filename prefix: ")
	exprt (getvar 'expert)
	ct    (getvar 'ctab)
	doc   (vla-Get-ActiveDocument
		(vlax-Get-Acad-Object)
	      )
	lays  (vla-get-layouts doc)
	msg   ""
  )
  (setvar 'filedia 0)
  (setvar 'expert 5)
  (setvar 'tilemode 1)
  (command "_ucs" "_w")
  (foreach l (layoutlist)
    (setvar 'ctab l)
    (if	(> (sslength (ssget "_x" (list (cons 410 (getvar 'ctab)))))
	   1
	)
      (progn
	(vla-EndUndoMark doc)
	(vla-StartUndoMark doc)
	(vlax-map-collection
	  lays
	  '(lambda (x)
	     (if (/= (getvar 'ctab) (vla-get-name x))
	       (vl-catch-all-apply 'vla-delete (list x))
	     )
	   )
	)
	(command "_-wblock" (strcat (getvar 'dwgprefix) pre l) "*")
	(setq
	  msg (strcat (getvar 'dwgprefix) pre l ".dwg created.\n" msg)
	)
	(vla-EndUndoMark doc)
	(command "_u")
      )
      (setq msg
	     (strcat "Tab " l " has nothing on it and skipped." "\n" msg)
      )
    )
  )
  (setvar 'filedia fda)
  (setvar 'expert exprt)
  (setvar 'ctab ct)
  (princ msg)
  (princ)
)

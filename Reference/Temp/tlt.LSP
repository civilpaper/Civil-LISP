(defun c:TLT ()
  (setq os (getvar "osmode"))
  (setq p (getpoint "\nChon diem dau: "))
  (setq p1 (getpoint "\nChon diem cuoi: " p))
  (cond ((null tphan) (setq tphan 2)))
  (setq dau1 (car p))
  (setq cuoi1 (cadr p))
  (setq dau2 (car p1))
  (setq cuoi2 (cadr p1))
  (setq lx (abs (- dau1 dau2)))
  (setq ly (abs (- cuoi1 cuoi2)))
  (setq i (/ lx ly))
  (setq caochu (getreal "\nnhap cao chu: "))
  (setvar "osmode" 0)
  (command "layer" "S" "0" "")
  (setq pt1 (polar p (angle p p1) (/ (distance p p1) 2)))
  (setq dau1 (+ 5 (car pt1)))
  (setq cuoi1 (cadr pt1))
  (setq goc (/ (* (angle p p1) 180) pi))
  (setq pt2 (polar pt1 (+ (angle p p1) (/ pi 2)) caochu))
  ;(setq chuoi (100/strcat (rtos i 2 tphan) "%"))
  (setq chuoi (strcat (rtos (* i 100) 2 2) "%" ))
  (command "text" "J" "M" pt2 caochu goc chuoi)
  (setvar "osmode" os)
)

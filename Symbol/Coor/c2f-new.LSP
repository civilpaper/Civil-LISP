(defun c:cr(/ ssa ssl i stt si sname os p1 p2 str1 str2)
  (setq unit (getvar "INSUNITS"))
  (setvar "INSUNITS" 4)
  (if (= ly_scale nil) (c:tl))
  (setq ss (ssadd))
  (if (= #Bacc nil) (setq #Bacc (getint "\nInput accuracy: ")))
  (setq CL (getvar "clayer"))
  (setvar "CLAYER" "0") 	
  (setq DZ (getvar "DIMZIN"))
  (setvar "DIMZIN" 0)
  (setq OT (getvar "ORTHOMODE"))
  (setvar "ORTHOMODE" 0)
  
  (setq ssa (ssget "x"))
  (setq ssl (sslength ssa))
  (setq i 0)
  (setq stt 0)
  (while (< i ssl)
    (setq si (cdr (assoc 0 (entget (ssname ssa i)))))
    (setq sname (cdr (assoc 2 (entget (ssname ssa i)))))
    (if (and (= si "INSERT") (= (substr sname 1 4) "coor")) (setq stt (+ stt 1)))
    (setq i (+ i 1))
  )
  (setq stt (+ stt 1))
  (setq pt (getpoint "\nInput point: ")
	ptside (getpoint "\nDirect: " pt)
	ang (angle pt ptside)
  )
  (setq os (getvar "OSMODE"))
  (setvar "OSMODE" 0)
  (if (AND (>= ang 0) (< ang 1.5708)) (command ".INSERT" "coor_RU" pt ly_scale ly_scale "0" (rtos stt 2 0)))
     ( if	 (AND (>= ang 1.5708) (< ang 3.1416)) (command ".INSERT" "coor_LU" pt ly_scale ly_scale "0" (rtos stt 2 0)))
     ( if	 (AND (>= ang 3.1416) (< ang 4.7124)) (command ".INSERT" "coor_LD" pt ly_scale ly_scale "0" (rtos stt 2 0)))
     ( if	 (AND (>= ang 4.7124) (< ang 6.2832)) (command ".INSERT" "coor_RD" pt ly_scale ly_scale "0" (rtos stt 2 0)))
  (setq ss (ssadd (entlast) ss))
  (bup ss)
  (setvar "DIMZIN" DZ)
  (setvar "ORTHOMODE" OT)
  (setvar "CLAYER" CL)
  (setvar "INSUNITS" unit)
  (setvar "OSMODE" os)
  (setvar "INSUNITS" unit)
)
;;;;;;;;;;;;;;;;;;;;;;;;;;;;;;;;;;;;;;;;;;;;;;;;;;;;;;;;;;;;;;;;;;;;

(defun c:coor_summary()
  (setq ss (ssget "x"))
  (setq ssl (sslength ss))
  (setq coor_ss (ssadd))
  (setq i 0)
  (while (< i ssl)
    (setq si (cdr (assoc 0 (entget (ssname ss i)))))
    (setq sname (cdr (assoc 2 (entget (ssname ss i)))))
    (if (and (= si "INSERT") (= (substr sname 1 4) "coor"))
      (progn
	(setq coor_ss (ssadd (ssname ss i) coor_ss))
      )
    )
    (setq i (+ i 1))
  )
  (setq all coor_ss)
  (setq all_len (sslength all))

 ;;;;;;;;;;;;;;
  
)


;;;;;;;;;;;;;;;;;;;;;;;;;;;;;;;;;;;;;;;;
;================================================================
;ham data lay du lieu
(defun c:lay(/ i)
  (setq all (ssget "x"))
  (setq all_len (sslength all))
  (setq i 0)
  (setq list_bb '())
  (while (< i all_len)
    (setq i_ename (ssname all i))
    (setq i_cat (cdr (assoc 0 (entget i_ename))))
    (if (= i_cat "INSERT")
      (progn
	(setq i_name (cdr (assoc 2 (entget i_ename))))
	(if (= (substr i_name 1 4) "coor")
	  (progn
	    (setq x (car (cdr (assoc 10 (entget i_ename)))))
	    (setq y (cadr (cdr (assoc 10 (entget i_ename)))))
	    (setq e (entnext i_ename))
	    (setq pn (cdr (assoc 1 (entget e))))
	    (setq list_att (list pn x y))
	    (if (/= list_att nil) (setq list_bb (cons list_att list_bb)))
	  )
	)
      )
    )
    (setq i (+ i 1))
  )
)
;================================================================
;================================================================
;===================================================================
;MAin Funtion
(defun c:tk()
  (c:lay)
  (chen_tk)
  ;(chen_th)
)
;=========================================



;het ham
;=========================================
(defun chen_tk(/ sxep1 ssl i j dchenx dcheny dchen ss ssl)
  (setq ssall (ssadd))
  (setq unit (getvar "INSUNITS"))
  (setvar "INSUNITS" 4)
  (setq listbb1 list_bb)
  (setq tk_pt (getpoint "\nInsert Table: "))
  (command ".insert" "coor_header" tk_pt ly_scale ly_scale 0)
  (command ".explode" "_l")
  (setq ss (ssget "p"))
  (setq l 0)
  (while (< l (sslength ss))
    (setq ssall (ssadd (ssname ss l) ssall))
    (setq l (+ l 1))
  )

  (setq i 0)
  (while (< i (length listbb1))
    (setq ai (nth i listbb1))
    (setq name (nth 0 ai))
    (setq x (nth 1 ai))
    (setq y (nth 2 ai))
    
    (setq dchenx (car tk_pt)
	  dcheny (- (cadr tk_pt) (* (* 2.6 ly_scale) i))
	  dchen (list dchenx dcheny)
    )

    (command ".insert" "coor_rows" dchen ly_scale ly_scale 0)
    (command ".explode" "_l")
    (setq ss (ssget "p"))
    (setq l 0)
    (while (< l (sslength ss))
      (setq ssall (ssadd (ssname ss l) ssall))
      (setq l (+ l 1))
    )
    (setq ssl (sslength ss))
    
    (setq j 0)
    (while (< j ssl)
      (setq ssj (ssname ss j))
      (setq list_ssj (entget ssj))
      (setq loai (dxf 0 (entget ssj)))
      (if (= loai "TEXT")
	(progn
	  (setq default (cdr (assoc 1 (entget ssj))))
	  (if (= default "name")
	    (progn
	      (setq old (cons 1 (cdr (assoc 1 list_ssj))))
	      (setq new (cons 1 name))
	      (setq list_ssj (subst new old list_ssj))
	      (entmod list_ssj)))
	  (if (= default "x")
	    (progn
	      (setq old (cons 1 (cdr (assoc 1 list_ssj))))
	      (setq new (cons 1 (rtos x 2 #Bacc)))
	      (setq list_ssj (subst new old list_ssj))
	      (entmod list_ssj)))
	  (if (= default "y")
	    (progn
	      (setq old (cons 1 (cdr (assoc 1 list_ssj))))
	      (setq new (cons 1 (rtos y 2 #Bacc)))
	      (setq list_ssj (subst new old list_ssj))
	      (entmod list_ssj)))
	)
      )
      (setq j (+ j 1))
    );dong while
    (setq i (+ i 1))
  );while
  (setq dchenx (car tk_pt)
	dcheny (- (cadr tk_pt) (* (* 2.6 ly_scale) i))
	dchen (list dchenx dcheny)
  )
  (command ".insert" "coor_footer" dchen ly_scale ly_scale 0)
  (command ".explode" "_l")
  (setq ss (ssget "p"))
  (setq l 0)
  (while (< l (sslength ss))
    (setq ssall (ssadd (ssname ss l) ssall))
    (setq l (+ l 1))
  )
  (setvar "OSMODE" os)
  (setvar "INSUNITS" unit)


)
